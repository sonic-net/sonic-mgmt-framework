module openconfig-network-instance-ext {

  yang-version "1";

  // namespace
  namespace "http://openconfig.net/yang/network-instance/extension";

  prefix "oc-netinst-ext";

  // import some basic types
  import openconfig-network-instance { prefix "oc-netinst"; }

  description
        "This module describes a YANG model for network instance
        configuration extensions.";

  revision "2019-10-29" {
    description
      "Add OpenConfig unsupported attributes.";
  }

  deviation /oc-netinst:network-instances/oc-netinst:network-instance/oc-netinst:inter-instance-policies {
      deviate not-supported;
  }

  deviation /oc-netinst:network-instances/oc-netinst:network-instance/oc-netinst:mpls {
      deviate not-supported;
  }
  
  deviation /oc-netinst:network-instances/oc-netinst:network-instance/oc-netinst:segment-routing {
      deviate not-supported;
  }

  deviation /oc-netinst:network-instances/oc-netinst:network-instance/oc-netinst:protocols/oc-netinst:protocol/oc-netinst:igmp {
      deviate not-supported;
  }

  deviation /oc-netinst:network-instances/oc-netinst:network-instance/oc-netinst:protocols/oc-netinst:protocol/oc-netinst:pim {
      deviate not-supported;
  }

  deviation /oc-netinst:network-instances/oc-netinst:network-instance/oc-netinst:protocols/oc-netinst:protocol/oc-netinst:isis {
      deviate not-supported;
  }
  
  deviation /oc-netinst:network-instances/oc-netinst:network-instance/oc-netinst:policy-forwarding {
	  deviate not-supported;
  }
  
}
