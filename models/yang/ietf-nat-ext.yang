module ietf-nat-ext {

    yang-version "1";

    // namespace
    namespace "urn:ietf:params:xml:ns:yang:ietf-nat:extension";

    prefix "ietf-nat-ext";

    import ietf-yang-types { prefix yang; }
    import ietf-nat { prefix ietf-nat; }
    import ietf-inet-types {prefix inet; }

    grouping nat-instance-ext {
        leaf nat_timeout {
            type uint32 {
                range "300..432000";
            }
        }
        leaf nat_tcp_timeout {
            type uint32 {
                range "300..432000";
            }
        }
        leaf nat_udp_timeout {
            type uint16 {
                range "120..600";
            }
        }
        container zone-counters {
            list zone-counter-entry {
                key "zone-id";
                leaf zone-id {
                    type uint8;
                }
                leaf nat-dnat-discards {
                    type yang:zero-based-counter64;
                }
                leaf nat-snat-discards {
                    type yang:zero-based-counter64;
                }
                leaf nat-dnat-translation-needed {
                    type yang:zero-based-counter64;
                }
                leaf nat-snat-translation-needed {
                    type yang:zero-based-counter64;
                }
                leaf nat-dnat-translations {
                    type yang:zero-based-counter64;
                }
                leaf nat-snat-translations {
                    type yang:zero-based-counter64;
                }
            }
        }
    }

    grouping nat-instance-nat-pool {
        container nat-pool {
            list nat-pool-entry {
                key "pool-name";

                leaf pool-name {
                    type string;
                }
                choice nat-ip {
                    case ip-address {
                        leaf IP-ADDRESS {
                            type inet:ipv4-address;
                        }
                    }
                    case ip-address-range {
                        leaf IP-ADDRESS-RANGE {
                            type string {
                                pattern '^(([0-9]|[1-9][0-9]|1[0-9][0-9]|2[0-4][0-9]|'  +
                                    '25[0-5])\.){3}([0-9]|[1-9][0-9]|1[0-9][0-9]|2[0-4]' +
                                    '[0-9]|25[0-5])$ (-) ^(([0-9]|[1-9][0-9]|1[0-9][0-9]|2[0-4][0-9]|'  +
                                    '25[0-5])\.){3}([0-9]|[1-9][0-9]|1[0-9][0-9]|2[0-4]'  +
                                    '[0-9]|25[0-5])$';
                            }
                        }
                    }
                }
                leaf nat-port {
                    type string {
                        pattern "[0-9]{1,5}(-)[0-9]{1,5}";
                    }
                }
            }
        }
    }

    grouping nat-instance-nat-bindings {
        container nat-bindings {
            list nat-binding-entry {
                key "binding-name";

                leaf binding-name {
                    type string;
                }
                leaf nat-pool {
                    mandatory true;
                    type string;
                }
                leaf access-list {
                    type string;
                }
                leaf nat-type {
                    type enumeration {
                        enum SNAT;
                        enum DNAT;
                    }
                    default SNAT;
                }
                leaf twice-nat-id {
                    type uint16 {
                        range "1..9999";
                    }
                }
            }
        }
    }

    grouping nat-instance-mapping-entry-ext {
        leaf twice_nat_id {
            type uint16 {
                range "1..9999";
            }
        }
        container statistics {
            config false;
            leaf dnat-translations-pkts {
                type yang:zero-based-counter64;
            }
            leaf dnat-translations-bytes {
                type yang:zero-based-counter64;
            }
            leaf snat-translations-pkts {
                type yang:zero-based-counter64;
            }
            leaf snat-translations-bytes {
                type yang:zero-based-counter64;
            }
        }
    }

    
    augment /ietf-nat:nat/ietf-nat:instances/ietf-nat:instance {
        uses nat-instance-ext;
        uses nat-instance-nat-pool;
        uses nat-instance-nat-bindings;
    }

    
    
    augment /ietf-nat:nat/ietf-nat:instances/ietf-nat:instance/ietf-nat:mapping-table/ietf-nat:mapping-entry {
        uses nat-instance-mapping-entry-ext;
    }
}
