module dell-intf-augments {

    yang-version "1";

    namespace "http://openconfig.net/yang/interfaces/aggregate-augment";

    prefix "if-agmnt";

    import openconfig-interfaces { prefix oc-if; }
    import openconfig-if-aggregate { prefix oc-lag; }
    import openconfig-if-ip {prefix oc-ip; }
    import openconfig-inet-types { prefix oc-inet; }
    import openconfig-lacp {prefix oc-lacp; }

    // meta
    organization "OpenConfig working group";

    contact
        "OpenConfig working group
        netopenconfig@googlegroups.com";

    description
        "Model for managing aggregated (aka bundle, LAG) interfaces.";

    revision 2019-10-03 {
        description
            "Initial augment file.";
    }

    // augment statements

    augment "/oc-if:interfaces/oc-if:interface/oc-lag:aggregation/oc-lag:config" {
        leaf fallback {
            type boolean;
            description "Indicating whether lacp fallback is enabled or not";
        }
    }
    augment "/oc-if:interfaces/oc-if:interface/oc-lag:aggregation/oc-lag:state" {
        leaf fallback {
            type boolean;
            description "Fallback status on this interface";
        }
    }
    augment "/oc-lacp:lacp/oc-lacp:interfaces/oc-lacp:interface/oc-lacp:members/oc-lacp:member/oc-lacp:state" {
        leaf selected {
            type boolean;
            description "Selected status on this interface";
        }
    }

    augment "/oc-if:interfaces/oc-if:interface/oc-if:subinterfaces/oc-if:subinterface/oc-ip:ipv4/oc-ip:addresses/oc-ip:address/oc-ip:config" {
        leaf gw-addr {
            type oc-inet:ipv4-address;
            description "IPv4 Gateway address";
        }
    }
    augment "/oc-if:interfaces/oc-if:interface/oc-if:subinterfaces/oc-if:subinterface/oc-ip:ipv4/oc-ip:addresses/oc-ip:address/oc-ip:state" {
        leaf gw-addr {
            type oc-inet:ipv4-address;
            description "IPv4 Gateway address";
        }
    }
    augment "/oc-if:interfaces/oc-if:interface/oc-if:subinterfaces/oc-if:subinterface/oc-ip:ipv6/oc-ip:addresses/oc-ip:address/oc-ip:config" {
        leaf gw-addr {
            type oc-inet:ipv6-address;
            description "IPv6 Gateway address";
        }
    }
    augment "/oc-if:interfaces/oc-if:interface/oc-if:subinterfaces/oc-if:subinterface/oc-ip:ipv6/oc-ip:addresses/oc-ip:address/oc-ip:state" {
        leaf gw-addr {
            type oc-inet:ipv6-address;
            description "IPv6 Gateway address";
        }
    }
}
