module sonic-vlan-annot {

    yang-version "1.1";

    namespace "http://openconfig.net/yang/vlan-annot";
    prefix "svlan-annot"; 

    import sonic-extensions { prefix sonic-ext; }
    import sonic-vlan { prefix svlan; }

    // meta
    organization
       "SONiC";

    contact
       "SONiC";

    description
       "SONIC VLAN";

    revision 2019-10-31 {
       description
          "Initial revision.";
    }

    deviation /svlan:sonic-vlan/svlan:VLAN_TABLE/svlan:VLAN_TABLE_LIST  {
      deviate add {
		sonic-ext:db-name "APPL_DB";
      }
    }

    deviation /svlan:sonic-vlan/svlan:VLAN_MEMBER_TABLE/svlan:VLAN_MEMBER_TABLE_LIST {
      deviate add {
        sonic-ext:db-name "APPL_DB";
      }
    }
}
