module sonic-interface-annot {

    yang-version "1.1";

    namespace "http://openconfig.net/yang/annotation/sintf-annot";
    prefix "sintf-annot";

    import sonic-extensions { prefix sonic-ext; }
    import sonic-interface { prefix sintf; }

    deviation /sintf:clear_counters {
        deviate add {
	    sonic-ext:rpc-callback "rpc_clear_counters";
        }
    }
    deviation /sintf:sonic-interface/sintf:INTF_TABLE {
        deviate add {
            sonic-ext:db-name "APPL_DB";
        }
    }

}
