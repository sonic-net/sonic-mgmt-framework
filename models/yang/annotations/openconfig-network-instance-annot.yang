module openconfig-network-instance-annot {

    yang-version "1";

    namespace "http://openconfig.net/yang/annotation/openconfig-network-instance-annot";
    prefix "oc-netinst-annot";

    import openconfig-network-instance { prefix oc-netinst; }
    import openconfig-network-instance-ext { prefix oc-netinst-ext; }
    import sonic-extensions { prefix sonic-ext; }
    import openconfig-network-instance-deviation { prefix oc-netinst-deviation; }
    import openconfig-bgp-ext { prefix oc-bgp-ext; }
    import openconfig-bgp-evpn-ext { prefix oc-bgp-evpn-ext; }
	
    import ietf-yang-types { prefix yang; }
    import openconfig-vxlan {prefix oc-vxlan; }

    deviation /oc-netinst:network-instances/oc-netinst:network-instance {
      deviate add {
        sonic-ext:table-transformer "network_instance_table_name_xfmr";
        sonic-ext:key-transformer "network_instance_table_key_xfmr";
      }
    }

    deviation /oc-netinst:network-instances/oc-netinst:network-instance/oc-netinst:name {
      deviate add {
          sonic-ext:field-transformer "network_instance_name_key_xfmr";
      }
    }

    deviation /oc-netinst:network-instances/oc-netinst:network-instance/oc-netinst:config/oc-netinst:name {
      deviate add {
        sonic-ext:field-transformer "network_instance_name_field_xfmr";
      }
    }

    deviation /oc-netinst:network-instances/oc-netinst:network-instance/oc-netinst:config/oc-netinst:type {
      deviate add {
        sonic-ext:field-transformer "network_instance_type_field_xfmr";
      }
    }

    deviation /oc-netinst:network-instances/oc-netinst:network-instance/oc-netinst:config/oc-netinst:enabled {
      deviate add {
        sonic-ext:field-transformer "network_instance_enabled_field_xfmr";
      }
    }

    deviation /oc-netinst:network-instances/oc-netinst:network-instance/oc-netinst:config/oc-netinst:mtu {
      deviate add {
        sonic-ext:field-transformer "network_instance_mtu_field_xfmr";
      }
    }

    deviation /oc-netinst:network-instances/oc-netinst:network-instance/oc-netinst:config/oc-netinst:enabled-address-families {
      deviate add {
        sonic-ext:field-transformer "network_instance_enabled_addr_family_field_xfmr";
      }
    }

    deviation /oc-netinst:network-instances/oc-netinst:network-instance/oc-netinst:config/oc-netinst:description {
      deviate add {
        sonic-ext:field-transformer "network_instance_description_field_xfmr";
      }
    }

    deviation /oc-netinst:network-instances/oc-netinst:network-instance/oc-netinst:config/oc-netinst:router-id {
      deviate add {
        sonic-ext:field-transformer "network_instance_router_id_field_xfmr";
      }
    }

    deviation /oc-netinst:network-instances/oc-netinst:network-instance/oc-netinst:config/oc-netinst:route-distinguisher {
      deviate add {
        sonic-ext:field-transformer "network_instance_route_distinguisher_field_xfmr";
      }
    }

    deviation /oc-netinst:network-instances/oc-netinst:network-instance/oc-netinst:state/oc-netinst:name {
      deviate add {
        sonic-ext:field-transformer "network_instance_name_field_xfmr";
      }
    }

    deviation /oc-netinst:network-instances/oc-netinst:network-instance/oc-netinst:state/oc-netinst:type {
      deviate add {
        sonic-ext:field-transformer "network_instance_type_field_xfmr";
      }
    }

    deviation /oc-netinst:network-instances/oc-netinst:network-instance/oc-netinst:state/oc-netinst:enabled-address-families {
      deviate add {
        sonic-ext:field-transformer "network_instance_enabled_addr_fam_field_xfmr";
      }
    }

    deviation /oc-netinst:network-instances/oc-netinst:network-instance/oc-netinst:state/oc-netinst:mtu {
      deviate add {
        sonic-ext:field-transformer "network_instance_mtu_field_xfmr";
      }
    }

    deviation /oc-netinst:network-instances/oc-netinst:network-instance/oc-netinst:state/oc-netinst:enabled {
      deviate add {
        sonic-ext:field-transformer "network_instance_enabled_field_xfmr";
      }
    }

    deviation /oc-netinst:network-instances/oc-netinst:network-instance/oc-netinst:state/oc-netinst:description {
      deviate add {
        sonic-ext:field-transformer "network_instance_description_field_xfmr";
      }
    }

    deviation /oc-netinst:network-instances/oc-netinst:network-instance/oc-netinst:state/oc-netinst:router-id {
      deviate add {
        sonic-ext:field-transformer "network_instance_router_id_field_xfmr";
      }
    }

    deviation /oc-netinst:network-instances/oc-netinst:network-instance/oc-netinst:state/oc-netinst:route-distinguisher {
      deviate add {
        sonic-ext:field-transformer "network_instance_route_distinguisher_field_xfmr";
      }
    }

    deviation /oc-netinst:network-instances/oc-netinst:network-instance/oc-netinst:interfaces/oc-netinst:interface {
      deviate add {
        sonic-ext:subtree-transformer "network_instance_interface_binding_subtree_xfmr";
      }
    }

    deviation /oc-netinst:network-instances/oc-netinst:network-instance/oc-netinst:fdb/oc-netinst:mac-table {
      deviate add {
            sonic-ext:db-name "APPL_DB";
            sonic-ext:subtree-transformer "fdb_mac_table_xfmr";
      }
    }
    
    deviation /oc-netinst:network-instances/oc-netinst:network-instance/oc-netinst:protocols {
        deviate add {
            sonic-ext:table-name "NONE";
        }
    }

    deviation /oc-netinst:network-instances/oc-netinst:network-instance/oc-netinst:protocols/oc-netinst:protocol {
        deviate add {
            sonic-ext:table-transformer "network_instance_protocols_ptotocol_table_name_xfmr";
            sonic-ext:key-transformer "network_instance_protocol_key_xfmr";
        }
    }


    deviation /oc-netinst:network-instances/oc-netinst:network-instance/oc-netinst:protocols/oc-netinst:protocol/oc-netinst:bgp/oc-netinst:global {
        deviate add {
            sonic-ext:db-name "CONFIG_DB";
            sonic-ext:table-name "BGP_GLOBALS";
            sonic-ext:key-transformer "bgp_gbl_tbl_key_xfmr";
        }
    }

    deviation /oc-netinst:network-instances/oc-netinst:network-instance/oc-netinst:protocols/oc-netinst:protocol/oc-netinst:bgp/oc-netinst:global/oc-netinst:config/oc-netinst:router-id {
        deviate add {
            sonic-ext:field-name "router_id";
        }
    }

    deviation /oc-netinst:network-instances/oc-netinst:network-instance/oc-netinst:protocols/oc-netinst:protocol/oc-netinst:bgp/oc-netinst:global/oc-netinst:config/oc-netinst:as {
        deviate add {
            sonic-ext:field-transformer "bgp_local_asn_fld_xfmr";
        }
    }

    deviation /oc-netinst:network-instances/oc-netinst:network-instance/oc-netinst:protocols/oc-netinst:protocol/oc-netinst:bgp/oc-netinst:global/oc-netinst:state {
        deviate add {
            sonic-ext:subtree-transformer "bgp_gbl_state_xfmr";
        }
    }

    deviation /oc-netinst:network-instances/oc-netinst:network-instance/oc-netinst:protocols/oc-netinst:protocol/oc-netinst:bgp/oc-netinst:global/oc-netinst:route-selection-options/oc-netinst:config/oc-netinst:always-compare-med {
      deviate add {
          sonic-ext:field-name "always_compare_med";
      }
    }

    deviation /oc-netinst:network-instances/oc-netinst:network-instance/oc-netinst:protocols/oc-netinst:protocol/oc-netinst:bgp/oc-netinst:global/oc-netinst:route-selection-options/oc-netinst:state/oc-netinst:always-compare-med {
      deviate add {
          sonic-ext:field-name "always_compare_med";
      }
    }

    deviation /oc-netinst:network-instances/oc-netinst:network-instance/oc-netinst:protocols/oc-netinst:protocol/oc-netinst:bgp/oc-netinst:global/oc-netinst:route-selection-options/oc-netinst:config/oc-netinst:ignore-as-path-length {
      deviate add {
          sonic-ext:field-name "ignore_as_path_length";
      }
    }

    deviation /oc-netinst:network-instances/oc-netinst:network-instance/oc-netinst:protocols/oc-netinst:protocol/oc-netinst:bgp/oc-netinst:global/oc-netinst:route-selection-options/oc-netinst:state/oc-netinst:ignore-as-path-length {
      deviate add {
          sonic-ext:field-name "ignore_as_path_length";
      }
    }

    deviation /oc-netinst:network-instances/oc-netinst:network-instance/oc-netinst:protocols/oc-netinst:protocol/oc-netinst:bgp/oc-netinst:global/oc-netinst:route-selection-options/oc-netinst:config/oc-netinst:external-compare-router-id {
      deviate add {
          sonic-ext:field-name "external_compare_router_id";
      }
    }

    deviation /oc-netinst:network-instances/oc-netinst:network-instance/oc-netinst:protocols/oc-netinst:protocol/oc-netinst:bgp/oc-netinst:global/oc-netinst:route-selection-options/oc-netinst:state/oc-netinst:external-compare-router-id {
      deviate add {
          sonic-ext:field-name "external_compare_router_id";
      }
    }

    deviation /oc-netinst:network-instances/oc-netinst:network-instance/oc-netinst:vlans {
      deviate add {
            sonic-ext:subtree-transformer "netinst_vlans_subtree_xfmr";
      }
    }

    deviation /oc-netinst:network-instances/oc-netinst:network-instance/oc-netinst:protocols/oc-netinst:protocol/oc-netinst:bgp/oc-netinst:global/oc-netinst:route-selection-options/oc-netinst:config/oc-bgp-ext:med-confed {
      deviate add {
          sonic-ext:field-name "med_confed";
      }
    }

    deviation /oc-netinst:network-instances/oc-netinst:network-instance/oc-netinst:protocols/oc-netinst:protocol/oc-netinst:bgp/oc-netinst:global/oc-netinst:route-selection-options/oc-netinst:state/oc-bgp-ext:med-confed {
      deviate add {
          sonic-ext:field-name "med_confed";
      }
    }

    deviation /oc-netinst:network-instances/oc-netinst:network-instance/oc-netinst:protocols/oc-netinst:protocol/oc-netinst:bgp/oc-netinst:global/oc-netinst:route-selection-options/oc-netinst:config/oc-bgp-ext:med-missing-as-worst {
      deviate add {
          sonic-ext:field-name "med_missing_as_worst";
      }
    }

    deviation /oc-netinst:network-instances/oc-netinst:network-instance/oc-netinst:protocols/oc-netinst:protocol/oc-netinst:bgp/oc-netinst:global/oc-netinst:route-selection-options/oc-netinst:state/oc-bgp-ext:med-missing-as-worst {
      deviate add {
          sonic-ext:field-name "med_missing_as_worst";
      }
    }

    deviation /oc-netinst:network-instances/oc-netinst:network-instance/oc-netinst:protocols/oc-netinst:protocol/oc-netinst:bgp/oc-netinst:global/oc-netinst:route-selection-options/oc-netinst:config/oc-bgp-ext:compare-confed-as-path {
      deviate add {
          sonic-ext:field-name "compare_confed_as_path";
      }
    }

    deviation /oc-netinst:network-instances/oc-netinst:network-instance/oc-netinst:protocols/oc-netinst:protocol/oc-netinst:bgp/oc-netinst:global/oc-netinst:route-selection-options/oc-netinst:state/oc-bgp-ext:compare-confed-as-path {
      deviate add {
          sonic-ext:field-name "compare_confed_as_path";
      }
    }

    deviation /oc-netinst:network-instances/oc-netinst:network-instance/oc-netinst:protocols/oc-netinst:protocol/oc-netinst:bgp/oc-netinst:global/oc-netinst:use-multiple-paths/oc-netinst:ebgp/oc-netinst:config/oc-netinst:allow-multiple-as {
      deviate add {
          sonic-ext:field-name "load_balance_mp_relax";
      }
    }

    deviation /oc-netinst:network-instances/oc-netinst:network-instance/oc-netinst:protocols/oc-netinst:protocol/oc-netinst:bgp/oc-netinst:global/oc-netinst:use-multiple-paths/oc-netinst:ebgp/oc-netinst:state/oc-netinst:allow-multiple-as {
      deviate add {
          sonic-ext:field-name "load_balance_mp_relax";
      }
    }

    deviation /oc-netinst:network-instances/oc-netinst:network-instance/oc-netinst:protocols/oc-netinst:protocol/oc-netinst:bgp/oc-netinst:global/oc-netinst:use-multiple-paths/oc-netinst:ebgp/oc-netinst:config/oc-bgp-ext:as-set {
      deviate add {
        sonic-ext:field-name "as_path_mp_as_set";
      }
    }


    deviation /oc-netinst:network-instances/oc-netinst:network-instance/oc-netinst:protocols/oc-netinst:protocol/oc-netinst:bgp/oc-netinst:global/oc-netinst:use-multiple-paths/oc-netinst:ebgp/oc-netinst:state/oc-bgp-ext:as-set {
      deviate add {
        sonic-ext:field-name "as_path_mp_as_set";
      }
    }

    deviation /oc-netinst:network-instances/oc-netinst:network-instance/oc-netinst:protocols/oc-netinst:protocol/oc-netinst:bgp/oc-netinst:global/oc-netinst:graceful-restart/oc-netinst:config/oc-netinst:enabled {
      deviate add {
          sonic-ext:field-name "graceful_restart_enable";
      }
    }

    deviation /oc-netinst:network-instances/oc-netinst:network-instance/oc-netinst:protocols/oc-netinst:protocol/oc-netinst:bgp/oc-netinst:global/oc-netinst:graceful-restart/oc-netinst:state/oc-netinst:enabled {
        deviate add {
          sonic-ext:field-name "graceful_restart_enable";
        }
    }


    deviation /oc-netinst:network-instances/oc-netinst:network-instance/oc-netinst:protocols/oc-netinst:protocol/oc-netinst:bgp/oc-netinst:global/oc-netinst:graceful-restart/oc-netinst:config/oc-netinst:restart-time {
      deviate add {
            sonic-ext:field-name "gr_restart_time";
      }
    }

    deviation /oc-netinst:network-instances/oc-netinst:network-instance/oc-netinst:protocols/oc-netinst:protocol/oc-netinst:bgp/oc-netinst:global/oc-netinst:graceful-restart/oc-netinst:state/oc-netinst:restart-time {
      deviate add {
            sonic-ext:field-name "gr_restart_time";
      }
    }

    deviation /oc-netinst:network-instances/oc-netinst:network-instance/oc-netinst:protocols/oc-netinst:protocol/oc-netinst:bgp/oc-netinst:global/oc-netinst:graceful-restart/oc-netinst:config/oc-netinst:stale-routes-time {
      deviate add {
            sonic-ext:field-name "gr_stale_routes_time";
      }
    }
    deviation /oc-netinst:network-instances/oc-netinst:network-instance/oc-netinst:protocols/oc-netinst:protocol/oc-netinst:bgp/oc-netinst:global/oc-netinst:graceful-restart/oc-netinst:state/oc-netinst:stale-routes-time {
      deviate add {
            sonic-ext:field-name "gr_stale_routes_time";
      }
    }

    deviation /oc-netinst:network-instances/oc-netinst:network-instance/oc-netinst:protocols/oc-netinst:protocol/oc-netinst:bgp/oc-netinst:global/oc-netinst:graceful-restart/oc-netinst:config/oc-bgp-ext:preserve-fw-state {
      deviate add {
          sonic-ext:field-name "gr_preserve_fw_state";
      }
    }

    deviation /oc-netinst:network-instances/oc-netinst:network-instance/oc-netinst:protocols/oc-netinst:protocol/oc-netinst:bgp/oc-netinst:global/oc-netinst:graceful-restart/oc-netinst:state/oc-bgp-ext:preserve-fw-state {
        deviate add {
          sonic-ext:field-name "gr_preserve_fw_state";
        }
    }

    deviation /oc-netinst:network-instances/oc-netinst:network-instance/oc-netinst:protocols/oc-netinst:protocol/oc-netinst:bgp/oc-netinst:global/oc-netinst:confederation/oc-netinst:config/oc-netinst:identifier {
      deviate add {
          sonic-ext:field-name "confed_id";
      }
    }

    deviation /oc-netinst:network-instances/oc-netinst:network-instance/oc-netinst:protocols/oc-netinst:protocol/oc-netinst:bgp/oc-netinst:global/oc-netinst:confederation/oc-netinst:config/oc-netinst:member-as {
      deviate add {
          sonic-ext:field-name "confed_peers";
      }
    }

    deviation /oc-netinst:network-instances/oc-netinst:network-instance/oc-netinst:protocols/oc-netinst:protocol/oc-netinst:bgp/oc-netinst:global/oc-netinst:confederation/oc-netinst:state/oc-netinst:identifier {
      deviate add {
          sonic-ext:field-name "confed_id";
      }
    }

    deviation /oc-netinst:network-instances/oc-netinst:network-instance/oc-netinst:protocols/oc-netinst:protocol/oc-netinst:bgp/oc-netinst:global/oc-netinst:confederation/oc-netinst:state/oc-netinst:member-as {
      deviate add {
          sonic-ext:field-name "confed_peers";
      }
    }

    deviation /oc-netinst:network-instances/oc-netinst:network-instance/oc-netinst:protocols/oc-netinst:protocol/oc-netinst:bgp/oc-netinst:neighbors {
      deviate add {	        
          sonic-ext:table-name "NONE";
      }	  
    }

    deviation /oc-netinst:network-instances/oc-netinst:network-instance/oc-netinst:protocols/oc-netinst:protocol/oc-netinst:bgp/oc-netinst:neighbors/oc-netinst:neighbor/oc-netinst:state {
        deviate add {
            sonic-ext:subtree-transformer "bgp_nbrs_nbr_state_xfmr";
        }
    }

    deviation /oc-netinst:network-instances/oc-netinst:network-instance/oc-netinst:protocols/oc-netinst:protocol/oc-netinst:bgp/oc-netinst:neighbors/oc-netinst:neighbor/oc-bgp-ext:auth-password {
        deviate add {
            sonic-ext:subtree-transformer "bgp_nbrs_nbr_auth_password_xfmr";
        }
    }

    deviation /oc-netinst:network-instances/oc-netinst:network-instance/oc-netinst:protocols/oc-netinst:protocol/oc-netinst:bgp/oc-netinst:peer-groups/oc-netinst:peer-group/oc-bgp-ext:auth-password {
        deviate add {
            sonic-ext:subtree-transformer "bgp_pgrp_auth_password_xfmr";
        }
    }

    deviation /oc-netinst:network-instances/oc-netinst:network-instance/oc-netinst:protocols/oc-netinst:protocol/oc-netinst:bgp/oc-netinst:neighbors/oc-netinst:neighbor/oc-netinst:timers/oc-netinst:state {
        deviate add {
            sonic-ext:subtree-transformer "bgp_nbrs_nbr_state_xfmr";
        }
    }

    deviation /oc-netinst:network-instances/oc-netinst:network-instance/oc-netinst:protocols/oc-netinst:protocol/oc-netinst:bgp/oc-netinst:neighbors/oc-netinst:neighbor/oc-netinst:transport/oc-netinst:state {
        deviate add {
            sonic-ext:subtree-transformer "bgp_nbrs_nbr_state_xfmr";
        }
    }

    deviation /oc-netinst:network-instances/oc-netinst:network-instance/oc-netinst:protocols/oc-netinst:protocol/oc-netinst:bgp/oc-netinst:neighbors/oc-netinst:neighbor/oc-netinst:afi-safis/oc-netinst:afi-safi/oc-netinst:state {
        deviate add {
            sonic-ext:subtree-transformer "bgp_nbrs_nbr_af_state_xfmr";
        }
    }

/* peer-groups->peer-group */
    deviation /oc-netinst:network-instances/oc-netinst:network-instance/oc-netinst:protocols/oc-netinst:protocol/oc-netinst:bgp/oc-netinst:peer-groups {
      deviate add {
            sonic-ext:table-name "NONE";
      }
    }

    deviation /oc-netinst:network-instances/oc-netinst:network-instance/oc-netinst:protocols/oc-netinst:protocol/oc-netinst:bgp/oc-netinst:peer-groups/oc-netinst:peer-group/oc-bgp-ext:members-state {
      deviate add {
	sonic-ext:subtree-transformer "bgp_peer_group_mbrs_state_xfmr";
      }
    }

/* peer-groups->peer-group */
    deviation /oc-netinst:network-instances/oc-netinst:network-instance/oc-netinst:protocols/oc-netinst:protocol/oc-netinst:bgp/oc-netinst:peer-groups/oc-netinst:peer-group {
      deviate add {
        sonic-ext:db-name "CONFIG_DB";
        sonic-ext:table-name "BGP_PEER_GROUP";
        sonic-ext:key-transformer "bgp_pgrp_tbl_key_xfmr";
      }
    }

    deviation /oc-netinst:network-instances/oc-netinst:network-instance/oc-netinst:protocols/oc-netinst:protocol/oc-netinst:bgp/oc-netinst:peer-groups/oc-netinst:peer-group/oc-netinst:config/oc-netinst:peer-group-name {
      deviate add {
            sonic-ext:field-transformer "bgp_pgrp_name_fld_xfmr";
      }
    }

/* peer-group->ebgp-multihop */
    deviation /oc-netinst:network-instances/oc-netinst:network-instance/oc-netinst:protocols/oc-netinst:protocol/oc-netinst:bgp/oc-netinst:peer-groups/oc-netinst:peer-group/oc-netinst:ebgp-multihop/oc-netinst:config/oc-netinst:multihop-ttl {
      deviate add {
            sonic-ext:field-name "ebgp_multihop_ttl";
      }
    }

    deviation /oc-netinst:network-instances/oc-netinst:network-instance/oc-netinst:protocols/oc-netinst:protocol/oc-netinst:bgp/oc-netinst:peer-groups/oc-netinst:peer-group/oc-netinst:ebgp-multihop/oc-netinst:config/oc-netinst:enabled {
      deviate add {
            sonic-ext:field-name "ebgp_multihop";
      }
    }

    deviation /oc-netinst:network-instances/oc-netinst:network-instance/oc-netinst:protocols/oc-netinst:protocol/oc-netinst:bgp/oc-netinst:peer-groups/oc-netinst:peer-group/oc-netinst:ebgp-multihop/oc-netinst:state/oc-netinst:enabled {
      deviate add {
            sonic-ext:field-name "ebgp_multihop";
      }
    }

    deviation /oc-netinst:network-instances/oc-netinst:network-instance/oc-netinst:protocols/oc-netinst:protocol/oc-netinst:bgp/oc-netinst:peer-groups/oc-netinst:peer-group/oc-netinst:ebgp-multihop/oc-netinst:state/oc-netinst:multihop-ttl {
      deviate add {
            sonic-ext:field-name "ebgp_multihop_ttl";
      }
    }

/* peer-group->timers */
/* peer-group->timers->state */
/* peer-groups->timers->state->hold-time */
    deviation /oc-netinst:network-instances/oc-netinst:network-instance/oc-netinst:protocols/oc-netinst:protocol/oc-netinst:bgp/oc-netinst:peer-groups/oc-netinst:peer-group/oc-netinst:timers/oc-netinst:state/oc-netinst:hold-time {
      deviate add {
            sonic-ext:field-name "holdtime";
      }
    }

/* peer-groups->timers->state->keepalive-interval */
    deviation /oc-netinst:network-instances/oc-netinst:network-instance/oc-netinst:protocols/oc-netinst:protocol/oc-netinst:bgp/oc-netinst:peer-groups/oc-netinst:peer-group/oc-netinst:timers/oc-netinst:state/oc-netinst:keepalive-interval {
      deviate add {
            sonic-ext:field-name "keepalive";
      }
    }

/* peer-groups->timers->state->minimum-advertisement-interval */
    deviation /oc-netinst:network-instances/oc-netinst:network-instance/oc-netinst:protocols/oc-netinst:protocol/oc-netinst:bgp/oc-netinst:peer-groups/oc-netinst:peer-group/oc-netinst:timers/oc-netinst:state/oc-netinst:minimum-advertisement-interval {
	      deviate add {
		    sonic-ext:field-name "min_adv_interval";
      }
    }

/* peer-groups->timers->state->connect-retry */
    deviation /oc-netinst:network-instances/oc-netinst:network-instance/oc-netinst:protocols/oc-netinst:protocol/oc-netinst:bgp/oc-netinst:peer-groups/oc-netinst:peer-group/oc-netinst:timers/oc-netinst:state/oc-netinst:connect-retry {
      deviate add {
            sonic-ext:field-name "conn_retry";
      }
    }

/* peer-group->timers->config */
/* peer-group->timers->config->minimum-advertisement-interval */
    deviation /oc-netinst:network-instances/oc-netinst:network-instance/oc-netinst:protocols/oc-netinst:protocol/oc-netinst:bgp/oc-netinst:peer-groups/oc-netinst:peer-group/oc-netinst:timers/oc-netinst:config/oc-netinst:minimum-advertisement-interval {
      deviate add {
            sonic-ext:field-name "min_adv_interval";
      }
    }

/* peer-group->timers->config->connect-retry */
    deviation /oc-netinst:network-instances/oc-netinst:network-instance/oc-netinst:protocols/oc-netinst:protocol/oc-netinst:bgp/oc-netinst:peer-groups/oc-netinst:peer-group/oc-netinst:timers/oc-netinst:config/oc-netinst:connect-retry {
      deviate add {
            sonic-ext:field-name "conn_retry";
      }
    }

/* peer-group->timers->config->hold-time */
    deviation /oc-netinst:network-instances/oc-netinst:network-instance/oc-netinst:protocols/oc-netinst:protocol/oc-netinst:bgp/oc-netinst:peer-groups/oc-netinst:peer-group/oc-netinst:timers/oc-netinst:config/oc-netinst:hold-time {
      deviate add {
            sonic-ext:field-name "holdtime";
      }
    }

/* peer-group->timers->config->keepalive-interval */
    deviation /oc-netinst:network-instances/oc-netinst:network-instance/oc-netinst:protocols/oc-netinst:protocol/oc-netinst:bgp/oc-netinst:peer-groups/oc-netinst:peer-group/oc-netinst:timers/oc-netinst:config/oc-netinst:keepalive-interval {
      deviate add {
            sonic-ext:field-name "keepalive";
      }
    }

/* peer-group->config */
/* peer-group->config->description */
    deviation /oc-netinst:network-instances/oc-netinst:network-instance/oc-netinst:protocols/oc-netinst:protocol/oc-netinst:bgp/oc-netinst:peer-groups/oc-netinst:peer-group/oc-netinst:config/oc-netinst:description {
      deviate add {
            sonic-ext:field-name "name";
      }
    }

/* peer-group->config->peer-as */
    deviation /oc-netinst:network-instances/oc-netinst:network-instance/oc-netinst:protocols/oc-netinst:protocol/oc-netinst:bgp/oc-netinst:peer-groups/oc-netinst:peer-group/oc-netinst:config/oc-netinst:peer-as {
      deviate add {
            sonic-ext:field-name "asn";
      }
    }

/* peer-group->config->peer-type */
    deviation /oc-netinst:network-instances/oc-netinst:network-instance/oc-netinst:protocols/oc-netinst:protocol/oc-netinst:bgp/oc-netinst:peer-groups/oc-netinst:peer-group/oc-netinst:config/oc-netinst:peer-type {
      deviate add {
            sonic-ext:field-transformer "bgp_pgrp_peer_type_fld_xfmr";
      }
    }

/* peer-group->config->local-as */
    deviation /oc-netinst:network-instances/oc-netinst:network-instance/oc-netinst:protocols/oc-netinst:protocol/oc-netinst:bgp/oc-netinst:peer-groups/oc-netinst:peer-group/oc-netinst:config/oc-netinst:local-as {
      deviate add {
            sonic-ext:field-name "local_asn";
      }
    }

/* peer-group->state */
/* peer-group->state->peer-group-name */
    deviation /oc-netinst:network-instances/oc-netinst:network-instance/oc-netinst:protocols/oc-netinst:protocol/oc-netinst:bgp/oc-netinst:peer-groups/oc-netinst:peer-group/oc-netinst:state/oc-netinst:peer-group-name {
      deviate add {
            sonic-ext:field-transformer "bgp_pgrp_name_fld_xfmr";
      }
    }

/* peer-group->state->description */
    deviation /oc-netinst:network-instances/oc-netinst:network-instance/oc-netinst:protocols/oc-netinst:protocol/oc-netinst:bgp/oc-netinst:peer-groups/oc-netinst:peer-group/oc-netinst:state/oc-netinst:description {
      deviate add {
            sonic-ext:field-name "name";
      }
    }

/* peer-group->state->local-as */
    deviation /oc-netinst:network-instances/oc-netinst:network-instance/oc-netinst:protocols/oc-netinst:protocol/oc-netinst:bgp/oc-netinst:peer-groups/oc-netinst:peer-group/oc-netinst:state/oc-netinst:local-as {
      deviate add {
            sonic-ext:field-name "local_asn";
      }
    }

/* peer-group->state->peer-as */
    deviation /oc-netinst:network-instances/oc-netinst:network-instance/oc-netinst:protocols/oc-netinst:protocol/oc-netinst:bgp/oc-netinst:peer-groups/oc-netinst:peer-group/oc-netinst:state/oc-netinst:peer-as {
      deviate add {
            sonic-ext:field-name "asn";
      }
    }

/* peer-group->state->peer-type */
    deviation /oc-netinst:network-instances/oc-netinst:network-instance/oc-netinst:protocols/oc-netinst:protocol/oc-netinst:bgp/oc-netinst:peer-groups/oc-netinst:peer-group/oc-netinst:state/oc-netinst:peer-type {
      deviate add {
            sonic-ext:field-transformer "bgp_pgrp_peer_type_fld_xfmr";
      }
    }

/* peer-group->transport */
/* peer-group->transport->state */
/* peer-group->transport->state->passive-mode */
    deviation /oc-netinst:network-instances/oc-netinst:network-instance/oc-netinst:protocols/oc-netinst:protocol/oc-netinst:bgp/oc-netinst:peer-groups/oc-netinst:peer-group/oc-netinst:transport/oc-netinst:state/oc-netinst:passive-mode {
      deviate add {
            sonic-ext:field-name "passive_mode";
      }
    }

/* peer-group->transport->state->local-address */
    deviation /oc-netinst:network-instances/oc-netinst:network-instance/oc-netinst:protocols/oc-netinst:protocol/oc-netinst:bgp/oc-netinst:peer-groups/oc-netinst:peer-group/oc-netinst:transport/oc-netinst:state/oc-netinst:local-address {
      deviate add {
            sonic-ext:field-name "local_addr";
      }
    }

    deviation /oc-netinst:network-instances/oc-netinst:network-instance/oc-netinst:protocols/oc-netinst:protocol/oc-netinst:bgp/oc-netinst:peer-groups/oc-netinst:peer-group/oc-netinst:state/oc-bgp-ext:enabled {
      deviate add {
            sonic-ext:field-name "admin_status";
      }
    }

/* peer-group->transport->config */
/* peer-group->transport->config->passive-mode */
    deviation /oc-netinst:network-instances/oc-netinst:network-instance/oc-netinst:protocols/oc-netinst:protocol/oc-netinst:bgp/oc-netinst:peer-groups/oc-netinst:peer-group/oc-netinst:transport/oc-netinst:config/oc-netinst:passive-mode {
      deviate add {
            sonic-ext:field-name "passive_mode";
      }
    }

/* peer-group->transport->config->local-address */
    deviation /oc-netinst:network-instances/oc-netinst:network-instance/oc-netinst:protocols/oc-netinst:protocol/oc-netinst:bgp/oc-netinst:peer-groups/oc-netinst:peer-group/oc-netinst:transport/oc-netinst:config/oc-netinst:local-address {
      deviate add {
            sonic-ext:field-name "local_addr";
      }
    }

    deviation /oc-netinst:network-instances/oc-netinst:network-instance/oc-netinst:protocols/oc-netinst:protocol/oc-netinst:bgp/oc-netinst:peer-groups/oc-netinst:peer-group/oc-netinst:config/oc-bgp-ext:enabled {
      deviate add {
            sonic-ext:field-name "admin_status";
      }
    }

/* peer-group->afi-safis->afi-safi */
    deviation /oc-netinst:network-instances/oc-netinst:network-instance/oc-netinst:protocols/oc-netinst:protocol/oc-netinst:bgp/oc-netinst:peer-groups/oc-netinst:peer-group/oc-netinst:afi-safis/oc-netinst:afi-safi {
      deviate add {
        sonic-ext:db-name "CONFIG_DB";
        sonic-ext:table-name "BGP_PEER_GROUP_AF";
        sonic-ext:key-transformer "bgp_af_pgrp_tbl_key_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn {
      deviate add {
        sonic-ext:key-transformer "bgp_af_pgrp_proto_tbl_key_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast {
      deviate add {
        sonic-ext:key-transformer "bgp_af_pgrp_proto_tbl_key_xfmr";
      }
    }
    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast {
      deviate add {
        sonic-ext:key-transformer "bgp_af_pgrp_proto_tbl_key_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:enabled {
      deviate add {
            sonic-ext:field-name "admin_status";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:enabled {
      deviate add {
            sonic-ext:field-name "admin_status";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:l2vpn-evpn/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-netinst:afi-safi-name {
      deviate add {
            sonic-ext:field-transformer "bgp_pgrp_afi_safi_name_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-netinst:afi-safi-name {
      deviate add {
            sonic-ext:field-transformer "bgp_pgrp_afi_safi_name_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:import-policy {
      deviate add {
            sonic-ext:field-name "route_map_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:state/oc-netinst:export-policy {
      deviate add {
            sonic-ext:field-name "route_map_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:import-policy {
      deviate add {
            sonic-ext:field-name "route_map_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:apply-policy/oc-netinst:config/oc-netinst:export-policy {
      deviate add {
            sonic-ext:field-name "route_map_out";
      }
    }

    deviation /oc-netinst:network-instances/oc-netinst:network-instance/oc-netinst:protocols/oc-netinst:protocol/oc-netinst:bgp/oc-netinst:global/oc-netinst:afi-safis/oc-netinst:afi-safi {
      deviate add {
        sonic-ext:table-name "BGP_GLOBALS_AF";
        sonic-ext:key-transformer "bgp_gbl_afi_safi_key_xfmr";
      }
    }

    deviation /oc-netinst:network-instances/oc-netinst:network-instance/oc-netinst:protocols/oc-netinst:protocol/oc-netinst:bgp/oc-netinst:global/oc-netinst:afi-safis/oc-netinst:afi-safi/oc-netinst:afi-safi-name {
      deviate add {
        sonic-ext:field-transformer "bgp_gbl_afi_safi_field_xfmr";
      }
    }

    deviation /oc-netinst:network-instances/oc-netinst:network-instance/oc-netinst:protocols/oc-netinst:protocol/oc-netinst:bgp/oc-netinst:global/oc-netinst:afi-safis/oc-netinst:afi-safi/oc-netinst:config/oc-netinst:afi-safi-name {
      deviate add {
        sonic-ext:field-transformer "bgp_gbl_afi_safi_field_xfmr";
      }
    }

    deviation /oc-netinst:network-instances/oc-netinst:network-instance/oc-netinst:protocols/oc-netinst:protocol/oc-netinst:bgp/oc-netinst:global/oc-netinst:afi-safis/oc-netinst:afi-safi/oc-netinst:state/oc-netinst:afi-safi-name {
      deviate add {
        sonic-ext:field-transformer "bgp_gbl_afi_safi_field_xfmr";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:config/oc-netinst:maximum-paths {
      deviate add {
        sonic-ext:field-name "max_ebgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:config/oc-netinst:maximum-paths {
      deviate add {
        sonic-ext:field-name "max_ibgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ebgp/oc-netinst:state/oc-netinst:maximum-paths {
      deviate add {
        sonic-ext:field-name "max_ebgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:state/oc-netinst:maximum-paths {
      deviate add {
        sonic-ext:field-name "max_ibgp_paths";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:config/oc-bgp-ext:equal-cluster-length {
      deviate add {
        sonic-ext:field-name "ibgp_equal_cluster_length";
      }
    }

    deviation /oc-netinst:network-instances/oc-netinst:network-instance/oc-netinst:protocols/oc-netinst:protocol/oc-netinst:bgp/oc-netinst:global/oc-netinst:afi-safis/oc-netinst:afi-safi/oc-netinst:use-multiple-paths/oc-netinst:ibgp/oc-netinst:state/oc-bgp-ext:equal-cluster-length {
      deviate add {
        sonic-ext:field-name "ibgp_equal_cluster_length";
      }
    }

    deviation /oc-netinst:network-instances/oc-netinst:network-instance/oc-netinst:table-connections {
      deviate add {
        sonic-ext:db-name "CONFIG_DB";
        sonic-ext:table-name "ROUTE_REDISTRIBUTE";
      }
    }

    deviation /oc-netinst:network-instances/oc-netinst:network-instance/oc-netinst:table-connections/oc-netinst:table-connection {
        deviate add {
            sonic-ext:key-transformer "route_table_conn_key_xfmr";
        }
    }

    deviation /oc-netinst:network-instances/oc-netinst:network-instance/oc-netinst:table-connections/oc-netinst:table-connection/oc-netinst:config/oc-netinst:src-protocol {
      deviate add {
        sonic-ext:field-name "src_protocol";
      }
    }

    deviation /oc-netinst:network-instances/oc-netinst:network-instance/oc-netinst:table-connections/oc-netinst:table-connection/oc-netinst:config/oc-netinst:dst-protocol {
      deviate add {
        sonic-ext:field-name "dst_protocol";
      }
    }
 
    deviation /oc-netinst:network-instances/oc-netinst:network-instance/oc-netinst:table-connections/oc-netinst:table-connection/oc-netinst:config/oc-netinst-ext:metric {
      deviate add {
        sonic-ext:field-name "metric";
      }
    }
   
    deviation /oc-netinst:network-instances/oc-netinst:network-instance/oc-netinst:table-connections/oc-netinst:table-connection/oc-netinst:config/oc-netinst:address-family {
      deviate add {
        sonic-ext:field-transformer "route_table_addr_family_xfmr";
      }
    }

    deviation /oc-netinst:network-instances/oc-netinst:network-instance/oc-netinst:table-connections/oc-netinst:table-connection/oc-netinst:config/oc-netinst:import-policy {
      deviate add {
        sonic-ext:field-name "route_map";
      }
    }

    deviation /oc-netinst:network-instances/oc-netinst:network-instance/oc-netinst:table-connections/oc-netinst:table-connection/oc-netinst:state/oc-netinst:src-protocol {
      deviate add {
        sonic-ext:field-name "src_protocol";
      }
    }

    deviation /oc-netinst:network-instances/oc-netinst:network-instance/oc-netinst:table-connections/oc-netinst:table-connection/oc-netinst:state/oc-netinst:dst-protocol {
      deviate add {
        sonic-ext:field-name "dst_protocol";
      }
    }
 
    deviation /oc-netinst:network-instances/oc-netinst:network-instance/oc-netinst:table-connections/oc-netinst:table-connection/oc-netinst:state/oc-netinst-ext:metric {
      deviate add {
        sonic-ext:field-name "metric";
      }
    }
   
    deviation /oc-netinst:network-instances/oc-netinst:network-instance/oc-netinst:table-connections/oc-netinst:table-connection/oc-netinst:state/oc-netinst:address-family {
      deviate add {
        sonic-ext:field-name "addr_family";
      }
    }

    deviation /oc-netinst:network-instances/oc-netinst:network-instance/oc-netinst:table-connections/oc-netinst:table-connection/oc-netinst:state/oc-netinst:import-policy {
      deviate add {
        sonic-ext:field-name "route_map";
      }
    }

    deviation /oc-netinst:network-instances/oc-netinst:network-instance/oc-netinst:protocols/oc-netinst:protocol/oc-netinst:bgp/oc-netinst:global/oc-netinst:dynamic-neighbor-prefixes/oc-netinst:dynamic-neighbor-prefix {
      deviate add {
        sonic-ext:table-name "BGP_GLOBALS_LISTEN_PREFIX";
        sonic-ext:key-transformer "bgp_dyn_neigh_listen_key_xfmr";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:prefix {
      deviate add {
        sonic-ext:field-transformer "bgp_dyn_neigh_listen_field_xfmr";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:config/oc-netinst:prefix {
      deviate add {
        sonic-ext:field-transformer "bgp_dyn_neigh_listen_field_xfmr";
      }
    }

    deviation /oc-netinst:network-instances/oc-netinst:network-instance/oc-netinst:protocols/oc-netinst:protocol/oc-netinst:bgp/oc-netinst:global/oc-netinst:dynamic-neighbor-prefixes/oc-netinst:dynamic-neighbor-prefix/oc-netinst:state/oc-netinst:prefix {
      deviate add {
        sonic-ext:field-transformer "bgp_dyn_neigh_listen_field_xfmr";
      }
    }


    deviation /oc-netinst:network-instances/oc-netinst:network-instance/oc-netinst:protocols/oc-netinst:protocol/oc-netinst:bgp/oc-netinst:global/oc-netinst:dynamic-neighbor-prefixes/oc-netinst:dynamic-neighbor-prefix/oc-netinst:config/oc-netinst:peer-group {
      deviate add {
        sonic-ext:field-name "peer_group";
      }
    }

    deviation /oc-netinst:network-instances/oc-netinst:network-instance/oc-netinst:protocols/oc-netinst:protocol/oc-netinst:bgp/oc-netinst:rib {
        deviate add {
            sonic-ext:table-name "NONE";
            sonic-ext:subtree-transformer "bgp_routes_get_xfmr";
        }
    }

    deviation /oc-netinst:network-instances/oc-netinst:network-instance/oc-netinst:protocols/oc-netinst:protocol/oc-netinst:bgp/oc-netinst:global/oc-bgp-ext:logging-options/oc-bgp-ext:config/oc-bgp-ext:log-neighbor-state-changes {
      deviate add {
            sonic-ext:field-name "log_nbr_state_changes";
      }
    }

    deviation /oc-netinst:network-instances/oc-netinst:network-instance/oc-netinst:protocols/oc-netinst:protocol/oc-netinst:bgp/oc-netinst:global/oc-bgp-ext:logging-options/oc-bgp-ext:state/oc-bgp-ext:log-neighbor-state-changes {
      deviate add {
            sonic-ext:field-name "log_nbr_state_changes";
      }
    }

    deviation /oc-netinst:network-instances/oc-netinst:network-instance/oc-netinst:protocols/oc-netinst:protocol/oc-netinst:bgp/oc-netinst:global/oc-bgp-ext:bgp-ext-route-reflector/oc-bgp-ext:config/oc-bgp-ext:route-reflector-cluster-id {
      deviate add {
            sonic-ext:field-name "rr_cluster_id";
      }
    }

    deviation /oc-netinst:network-instances/oc-netinst:network-instance/oc-netinst:protocols/oc-netinst:protocol/oc-netinst:bgp/oc-netinst:global/oc-bgp-ext:bgp-ext-route-reflector/oc-bgp-ext:config/oc-bgp-ext:allow-outbound-policy {
      deviate add {
            sonic-ext:field-name "rr_allow_out_policy";
      }
    }

    deviation /oc-netinst:network-instances/oc-netinst:network-instance/oc-netinst:protocols/oc-netinst:protocol/oc-netinst:bgp/oc-netinst:global/oc-bgp-ext:bgp-ext-route-reflector/oc-bgp-ext:state/oc-bgp-ext:route-reflector-cluster-id {
      deviate add {
            sonic-ext:field-name "rr_cluster_id";
      }
    }

    deviation /oc-netinst:network-instances/oc-netinst:network-instance/oc-netinst:protocols/oc-netinst:protocol/oc-netinst:bgp/oc-netinst:global/oc-bgp-ext:bgp-ext-route-reflector/oc-bgp-ext:state/oc-bgp-ext:allow-outbound-policy {
      deviate add {
            sonic-ext:field-name "rr_allow_out_policy";
      }
    }

    deviation /oc-netinst:network-instances/oc-netinst:network-instance/oc-netinst:protocols/oc-netinst:protocol/oc-netinst:bgp/oc-netinst:global/oc-netinst:config/oc-bgp-ext:disable-ebgp-connected-route-check {
      deviate add {
            sonic-ext:field-name "disable_ebgp_connected_rt_check";
      }
    }

    deviation /oc-netinst:network-instances/oc-netinst:network-instance/oc-netinst:protocols/oc-netinst:protocol/oc-netinst:bgp/oc-netinst:global/oc-netinst:config/oc-bgp-ext:fast-external-failover {
      deviate add {
            sonic-ext:field-name "fast_external_failover";
      }
    }

    deviation /oc-netinst:network-instances/oc-netinst:network-instance/oc-netinst:protocols/oc-netinst:protocol/oc-netinst:bgp/oc-netinst:global/oc-netinst:config/oc-bgp-ext:network-import-check {
      deviate add {
            sonic-ext:field-name "network_import_check";
      }
    }

    deviation /oc-netinst:network-instances/oc-netinst:network-instance/oc-netinst:protocols/oc-netinst:protocol/oc-netinst:bgp/oc-netinst:global/oc-netinst:config/oc-bgp-ext:graceful-shutdown {
      deviate add {
            sonic-ext:field-name "graceful_shutdown";
      }
    }

    deviation /oc-netinst:network-instances/oc-netinst:network-instance/oc-netinst:protocols/oc-netinst:protocol/oc-netinst:bgp/oc-netinst:global/oc-netinst:config/oc-bgp-ext:clnt-to-clnt-reflection {
      deviate add {
            sonic-ext:field-name "rr_clnt_to_clnt_reflection";
      }
    }


    deviation /oc-netinst:network-instances/oc-netinst:network-instance/oc-netinst:protocols/oc-netinst:protocol/oc-netinst:bgp/oc-netinst:global/oc-netinst:config/oc-bgp-ext:max-dynamic-neighbors {
      deviate add {
            sonic-ext:field-name "max_dynamic_neighbors";
      }
    }

    deviation /oc-netinst:network-instances/oc-netinst:network-instance/oc-netinst:protocols/oc-netinst:protocol/oc-netinst:bgp/oc-netinst:global/oc-netinst:config/oc-bgp-ext:read-quanta {
      deviate add {
            sonic-ext:field-name "read_quanta";
      }
    }

    deviation /oc-netinst:network-instances/oc-netinst:network-instance/oc-netinst:protocols/oc-netinst:protocol/oc-netinst:bgp/oc-netinst:global/oc-netinst:config/oc-bgp-ext:write-quanta {
      deviate add {
            sonic-ext:field-name "write_quanta";
      }
    }

    deviation /oc-netinst:network-instances/oc-netinst:network-instance/oc-netinst:protocols/oc-netinst:protocol/oc-netinst:bgp/oc-netinst:global/oc-netinst:config/oc-bgp-ext:coalesce-time {
      deviate add {
            sonic-ext:field-name "coalesce_time";
      }
    }

    deviation /oc-netinst:network-instances/oc-netinst:network-instance/oc-netinst:protocols/oc-netinst:protocol/oc-netinst:bgp/oc-netinst:global/oc-netinst:config/oc-bgp-ext:route-map-process-delay {
      deviate add {
            sonic-ext:field-name "route_map_process_delay";
      }
    }

    deviation /oc-netinst:network-instances/oc-netinst:network-instance/oc-netinst:protocols/oc-netinst:protocol/oc-netinst:bgp/oc-netinst:global/oc-netinst:config/oc-bgp-ext:deterministic-med {
      deviate add {
            sonic-ext:field-name "deterministic_med";
      }
    }


    deviation /oc-netinst:network-instances/oc-netinst:network-instance/oc-netinst:protocols/oc-netinst:protocol/oc-netinst:bgp/oc-netinst:global/oc-netinst:state/oc-bgp-ext:disable-ebgp-connected-route-check {
      deviate add {
            sonic-ext:field-name "disable_ebgp_connected_rt_check";
      }
    }

    deviation /oc-netinst:network-instances/oc-netinst:network-instance/oc-netinst:protocols/oc-netinst:protocol/oc-netinst:bgp/oc-netinst:global/oc-netinst:state/oc-bgp-ext:fast-external-failover {
      deviate add {
            sonic-ext:field-name "fast_external_failover";
      }
    }

    deviation /oc-netinst:network-instances/oc-netinst:network-instance/oc-netinst:protocols/oc-netinst:protocol/oc-netinst:bgp/oc-netinst:global/oc-netinst:state/oc-bgp-ext:network-import-check {
      deviate add {
            sonic-ext:field-name "network_import_check";
      }
    }

    deviation /oc-netinst:network-instances/oc-netinst:network-instance/oc-netinst:protocols/oc-netinst:protocol/oc-netinst:bgp/oc-netinst:global/oc-netinst:state/oc-bgp-ext:graceful-shutdown {
      deviate add {
            sonic-ext:field-name "graceful_shutdown";
      }
    }

    deviation /oc-netinst:network-instances/oc-netinst:network-instance/oc-netinst:protocols/oc-netinst:protocol/oc-netinst:bgp/oc-netinst:global/oc-netinst:state/oc-bgp-ext:clnt-to-clnt-reflection {
      deviate add {
            sonic-ext:field-name "rr_clnt_to_clnt_reflection";
      }
    }


    deviation /oc-netinst:network-instances/oc-netinst:network-instance/oc-netinst:protocols/oc-netinst:protocol/oc-netinst:bgp/oc-netinst:global/oc-netinst:state/oc-bgp-ext:max-dynamic-neighbors {
      deviate add {
            sonic-ext:field-name "max_dynamic_neighbors";
      }
    }

    deviation /oc-netinst:network-instances/oc-netinst:network-instance/oc-netinst:protocols/oc-netinst:protocol/oc-netinst:bgp/oc-netinst:global/oc-netinst:state/oc-bgp-ext:read-quanta {
      deviate add {
            sonic-ext:field-name "read_quanta";
      }
    }

    deviation /oc-netinst:network-instances/oc-netinst:network-instance/oc-netinst:protocols/oc-netinst:protocol/oc-netinst:bgp/oc-netinst:global/oc-netinst:state/oc-bgp-ext:write-quanta {
      deviate add {
            sonic-ext:field-name "write_quanta";
      }
    }

    deviation /oc-netinst:network-instances/oc-netinst:network-instance/oc-netinst:protocols/oc-netinst:protocol/oc-netinst:bgp/oc-netinst:global/oc-netinst:state/oc-bgp-ext:coalesce-time {
      deviate add {
            sonic-ext:field-name "coalesce_time";
      }
    }

    deviation /oc-netinst:network-instances/oc-netinst:network-instance/oc-netinst:protocols/oc-netinst:protocol/oc-netinst:bgp/oc-netinst:global/oc-netinst:state/oc-bgp-ext:route-map-process-delay {
      deviate add {
            sonic-ext:field-name "route_map_process_delay";
      }
    }

    deviation /oc-netinst:network-instances/oc-netinst:network-instance/oc-netinst:protocols/oc-netinst:protocol/oc-netinst:bgp/oc-netinst:global/oc-netinst:state/oc-bgp-ext:deterministic-med {
      deviate add {
            sonic-ext:field-name "deterministic_med";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:config/oc-bgp-ext:enabled {
      deviate add {
            sonic-ext:field-name "route_flap_dampen";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:config/oc-bgp-ext:half-life {
      deviate add {
            sonic-ext:field-name "route_flap_dampen_half_life";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:config/oc-bgp-ext:reuse-threshold {
      deviate add {
            sonic-ext:field-name "route_flap_dampen_reuse_threshold";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:config/oc-bgp-ext:suppress-threshold {
      deviate add {
            sonic-ext:field-name "route_flap_dampen_suppress_threshold";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:config/oc-bgp-ext:max-suppress {
      deviate add {
            sonic-ext:field-name "route_flap_dampen_max_suppress";
      }
    }


    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:state/oc-bgp-ext:enabled {
      deviate add {
            sonic-ext:field-name "route_flap_dampen";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:state/oc-bgp-ext:half-life {
      deviate add {
            sonic-ext:field-name "route_flap_dampen_half_life";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:state/oc-bgp-ext:reuse-threshold {
      deviate add {
            sonic-ext:field-name "route_flap_dampen_reuse_threshold";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:state/oc-bgp-ext:suppress-threshold {
      deviate add {
            sonic-ext:field-name "route_flap_dampen_suppress_threshold";
      }
    }

    deviation /oc-netinst:network-instances/oc-netinst:network-instance/oc-netinst:protocols/oc-netinst:protocol/oc-netinst:bgp/oc-netinst:global/oc-netinst:afi-safis/oc-netinst:afi-safi/oc-bgp-ext:route-flap-damping/oc-bgp-ext:state/oc-bgp-ext:max-suppress {
      deviate add {
            sonic-ext:field-name "route_flap_dampen_max_suppress";
      }
    }

    deviation /oc-netinst:network-instances/oc-netinst:network-instance/oc-netinst:protocols/oc-netinst:protocol/oc-netinst:bgp/oc-netinst:global/oc-bgp-ext:global-defaults/oc-bgp-ext:config/oc-bgp-ext:ipv4-unicast {
      deviate add {
            sonic-ext:field-name "default_ipv4_unicast";
      }
    }


    deviation /oc-netinst:network-instances/oc-netinst:network-instance/oc-netinst:protocols/oc-netinst:protocol/oc-netinst:bgp/oc-netinst:global/oc-bgp-ext:global-defaults/oc-bgp-ext:config/oc-bgp-ext:local-preference {
      deviate add {
            sonic-ext:field-name "default_local_preference";
      }
    }

    deviation /oc-netinst:network-instances/oc-netinst:network-instance/oc-netinst:protocols/oc-netinst:protocol/oc-netinst:bgp/oc-netinst:global/oc-bgp-ext:global-defaults/oc-bgp-ext:config/oc-bgp-ext:show-hostname {
      deviate add {
            sonic-ext:field-name "default_show_hostname";
      }
    }

    deviation /oc-netinst:network-instances/oc-netinst:network-instance/oc-netinst:protocols/oc-netinst:protocol/oc-netinst:bgp/oc-netinst:global/oc-bgp-ext:global-defaults/oc-bgp-ext:config/oc-bgp-ext:shutdown {
      deviate add {
            sonic-ext:field-name "default_shutdown";
      }
    }

    deviation /oc-netinst:network-instances/oc-netinst:network-instance/oc-netinst:protocols/oc-netinst:protocol/oc-netinst:bgp/oc-netinst:global/oc-bgp-ext:global-defaults/oc-bgp-ext:config/oc-bgp-ext:subgroup-pkt-queue-max {
      deviate add {
            sonic-ext:field-name "default_subgroup_pkt_queue_max";
      }
    }

    deviation /oc-netinst:network-instances/oc-netinst:network-instance/oc-netinst:protocols/oc-netinst:protocol/oc-netinst:bgp/oc-netinst:global/oc-bgp-ext:global-defaults/oc-bgp-ext:state/oc-bgp-ext:ipv4-unicast {
      deviate add {
            sonic-ext:field-name "default_ipv4_unicast";
      }
    }

    deviation /oc-netinst:network-instances/oc-netinst:network-instance/oc-netinst:protocols/oc-netinst:protocol/oc-netinst:bgp/oc-netinst:global/oc-bgp-ext:global-defaults/oc-bgp-ext:state/oc-bgp-ext:local-preference {
      deviate add {
            sonic-ext:field-name "default_local_preference";
      }
    }

    deviation /oc-netinst:network-instances/oc-netinst:network-instance/oc-netinst:protocols/oc-netinst:protocol/oc-netinst:bgp/oc-netinst:global/oc-bgp-ext:global-defaults/oc-bgp-ext:state/oc-bgp-ext:show-hostname {
      deviate add {
            sonic-ext:field-name "default_show_hostname";
      }
    }

    deviation /oc-netinst:network-instances/oc-netinst:network-instance/oc-netinst:protocols/oc-netinst:protocol/oc-netinst:bgp/oc-netinst:global/oc-bgp-ext:global-defaults/oc-bgp-ext:state/oc-bgp-ext:shutdown {
      deviate add {
            sonic-ext:field-name "default_shutdown";
      }
    }

    deviation /oc-netinst:network-instances/oc-netinst:network-instance/oc-netinst:protocols/oc-netinst:protocol/oc-netinst:bgp/oc-netinst:global/oc-bgp-ext:global-defaults/oc-bgp-ext:state/oc-bgp-ext:subgroup-pkt-queue-max {
      deviate add {
            sonic-ext:field-name "default_subgroup_pkt_queue_max";
      }
    }

    deviation /oc-netinst:network-instances/oc-netinst:network-instance/oc-netinst:protocols/oc-netinst:protocol/oc-netinst:bgp/oc-netinst:global/oc-bgp-ext:update-delay/oc-bgp-ext:config/oc-bgp-ext:max-delay {
      deviate add {
            sonic-ext:field-name "max_delay";
      }
    }

    deviation /oc-netinst:network-instances/oc-netinst:network-instance/oc-netinst:protocols/oc-netinst:protocol/oc-netinst:bgp/oc-netinst:global/oc-bgp-ext:update-delay/oc-bgp-ext:config/oc-bgp-ext:establish-wait {
      deviate add {
            sonic-ext:field-name "establish_wait";
      }
    }

    deviation /oc-netinst:network-instances/oc-netinst:network-instance/oc-netinst:protocols/oc-netinst:protocol/oc-netinst:bgp/oc-netinst:global/oc-bgp-ext:update-delay/oc-bgp-ext:state/oc-bgp-ext:max-delay {
      deviate add {
            sonic-ext:field-name "max_delay";
      }
    }

    deviation /oc-netinst:network-instances/oc-netinst:network-instance/oc-netinst:protocols/oc-netinst:protocol/oc-netinst:bgp/oc-netinst:global/oc-bgp-ext:update-delay/oc-bgp-ext:state/oc-bgp-ext:establish-wait {
      deviate add {
            sonic-ext:field-name "establish_wait";
      }
    }

    deviation /oc-netinst:network-instances/oc-netinst:network-instance/oc-netinst:protocols/oc-netinst:protocol/oc-netinst:bgp/oc-netinst:global/oc-bgp-ext:max-med/oc-bgp-ext:config/oc-bgp-ext:time {
      deviate add {
            sonic-ext:field-name "max_med_time";
      }
    }

    deviation /oc-netinst:network-instances/oc-netinst:network-instance/oc-netinst:protocols/oc-netinst:protocol/oc-netinst:bgp/oc-netinst:global/oc-bgp-ext:max-med/oc-bgp-ext:config/oc-bgp-ext:max-med-val {
      deviate add {
            sonic-ext:field-name "max_med_val";
      }
    }

    deviation /oc-netinst:network-instances/oc-netinst:network-instance/oc-netinst:protocols/oc-netinst:protocol/oc-netinst:bgp/oc-netinst:global/oc-bgp-ext:max-med/oc-bgp-ext:config/oc-bgp-ext:administrative {
      deviate add {
            sonic-ext:field-name "max_med_admin";
      }
    }

    deviation /oc-netinst:network-instances/oc-netinst:network-instance/oc-netinst:protocols/oc-netinst:protocol/oc-netinst:bgp/oc-netinst:global/oc-bgp-ext:max-med/oc-bgp-ext:config/oc-bgp-ext:admin-max-med-val {
      deviate add {
            sonic-ext:field-name "max_med_admin_val";
      }
    }


    deviation /oc-netinst:network-instances/oc-netinst:network-instance/oc-netinst:protocols/oc-netinst:protocol/oc-netinst:bgp/oc-netinst:global/oc-bgp-ext:max-med/oc-bgp-ext:state/oc-bgp-ext:administrative {
      deviate add {
            sonic-ext:field-name "max_med_admin";
      }
    }

    deviation /oc-netinst:network-instances/oc-netinst:network-instance/oc-netinst:protocols/oc-netinst:protocol/oc-netinst:bgp/oc-netinst:global/oc-bgp-ext:max-med/oc-bgp-ext:state/oc-bgp-ext:admin-max-med-val {
      deviate add {
            sonic-ext:field-name "max_med_admin_val";
      }
    }

    deviation /oc-netinst:network-instances/oc-netinst:network-instance/oc-netinst:protocols/oc-netinst:protocol/oc-netinst:bgp/oc-netinst:global/oc-bgp-ext:max-med/oc-bgp-ext:state/oc-bgp-ext:time {
      deviate add {
            sonic-ext:field-name "max_med_time";
      }
    }

    deviation /oc-netinst:network-instances/oc-netinst:network-instance/oc-netinst:protocols/oc-netinst:protocol/oc-netinst:bgp/oc-netinst:global/oc-bgp-ext:max-med/oc-bgp-ext:state/oc-bgp-ext:max-med-val {
      deviate add {
            sonic-ext:field-name "max_med_val";
      }
    }
    
    deviation /oc-netinst:network-instances/oc-netinst:network-instance/oc-netinst:protocols/oc-netinst:protocol/oc-netinst:bgp/oc-netinst:global/oc-netinst:config/oc-bgp-ext:hold-time {
      deviate add {
            sonic-ext:field-name "holdtime";
      }
    }
    
    deviation /oc-netinst:network-instances/oc-netinst:network-instance/oc-netinst:protocols/oc-netinst:protocol/oc-netinst:bgp/oc-netinst:global/oc-netinst:config/oc-bgp-ext:keepalive-interval {
      deviate add {
            sonic-ext:field-name "keepalive";
      }
    }
 
    deviation /oc-netinst:network-instances/oc-netinst:network-instance/oc-netinst:protocols/oc-netinst:protocol/oc-netinst:bgp/oc-netinst:global/oc-netinst:state/oc-bgp-ext:hold-time {
      deviate add {
            sonic-ext:field-name "holdtime";
      }
    }
    
    deviation /oc-netinst:network-instances/oc-netinst:network-instance/oc-netinst:protocols/oc-netinst:protocol/oc-netinst:bgp/oc-netinst:global/oc-netinst:state/oc-bgp-ext:keepalive-interval {
      deviate add {
            sonic-ext:field-name "keepalive";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address {
      deviate add {
        sonic-ext:table-name "BGP_GLOBALS_AF_AGGREGATE_ADDR";
        sonic-ext:key-transformer "bgp_gbl_afi_safi_addr_key_xfmr";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:prefix {
      deviate add {
            sonic-ext:field-transformer "bgp_gbl_afi_safi_addr_field_xfmr";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:config/oc-bgp-ext:prefix {
      deviate add {
            sonic-ext:field-transformer "bgp_gbl_afi_safi_addr_field_xfmr";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:state/oc-bgp-ext:prefix {
      deviate add {
            sonic-ext:field-transformer "bgp_gbl_afi_safi_addr_field_xfmr";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:config/oc-bgp-ext:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:state/oc-bgp-ext:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:config/oc-bgp-ext:as-set {
      deviate add {
            sonic-ext:field-name "as_set";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:state/oc-bgp-ext:as-set {
      deviate add {
            sonic-ext:field-name "as_set";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:config/oc-bgp-ext:summary-only {
      deviate add {
            sonic-ext:field-name "summary_only";
      }
    }

    deviation /oc-netinst:network-instances/oc-netinst:network-instance/oc-netinst:protocols/oc-netinst:protocol/oc-netinst:bgp/oc-netinst:global/oc-netinst:afi-safis/oc-netinst:afi-safi/oc-bgp-ext:aggregate-address-config/oc-bgp-ext:aggregate-address/oc-bgp-ext:state/oc-bgp-ext:summary-only {
      deviate add {
            sonic-ext:field-name "summary_only";
      }
    }

    deviation /oc-netinst:network-instances/oc-netinst:network-instance/oc-netinst:protocols/oc-netinst:protocol/oc-netinst:bgp/oc-netinst:global/oc-netinst:afi-safis/oc-netinst:afi-safi/oc-bgp-ext:default-route-distance/oc-bgp-ext:config/oc-bgp-ext:external-route-distance {
        deviate add {
            sonic-ext:field-name "ebgp_route_distance";
        }
    }

    deviation /oc-netinst:network-instances/oc-netinst:network-instance/oc-netinst:protocols/oc-netinst:protocol/oc-netinst:bgp/oc-netinst:global/oc-netinst:afi-safis/oc-netinst:afi-safi/oc-bgp-ext:default-route-distance/oc-bgp-ext:state/oc-bgp-ext:external-route-distance {
        deviate add {
            sonic-ext:field-name "ebgp_route_distance";
        }
    }

    deviation /oc-netinst:network-instances/oc-netinst:network-instance/oc-netinst:protocols/oc-netinst:protocol/oc-netinst:bgp/oc-netinst:global/oc-netinst:afi-safis/oc-netinst:afi-safi/oc-bgp-ext:default-route-distance/oc-bgp-ext:config/oc-bgp-ext:internal-route-distance {
        deviate add {
            sonic-ext:field-name "ibgp_route_distance";
        }
    }

    deviation /oc-netinst:network-instances/oc-netinst:network-instance/oc-netinst:protocols/oc-netinst:protocol/oc-netinst:bgp/oc-netinst:global/oc-netinst:afi-safis/oc-netinst:afi-safi/oc-bgp-ext:default-route-distance/oc-bgp-ext:state/oc-bgp-ext:internal-route-distance {
        deviate add {
            sonic-ext:field-name "ibgp_route_distance";
        }
    }

    deviation /oc-netinst:network-instances/oc-netinst:network-instance/oc-netinst:protocols/oc-netinst:protocol/oc-netinst:bgp/oc-netinst:global/oc-netinst:afi-safis/oc-netinst:afi-safi/oc-bgp-ext:default-route-distance/oc-bgp-ext:config/oc-bgp-ext:local-route-distance {
        deviate add {
            sonic-ext:field-name "local_route_distance";
        }
    }

    deviation /oc-netinst:network-instances/oc-netinst:network-instance/oc-netinst:protocols/oc-netinst:protocol/oc-netinst:bgp/oc-netinst:global/oc-netinst:afi-safis/oc-netinst:afi-safi/oc-bgp-ext:default-route-distance/oc-bgp-ext:state/oc-bgp-ext:local-route-distance {
        deviate add {
            sonic-ext:field-name "local_route_distance";
        }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network {
        deviate add {
            sonic-ext:table-name "BGP_GLOBALS_AF_NETWORK";
            sonic-ext:key-transformer "bgp_gbl_afi_safi_addr_key_xfmr";
        }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:prefix {
      deviate add {
            sonic-ext:field-transformer "bgp_gbl_afi_safi_addr_field_xfmr";
      }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:config/oc-bgp-ext:prefix {
      deviate add {
            sonic-ext:field-transformer "bgp_gbl_afi_safi_addr_field_xfmr";
      }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:state/oc-bgp-ext:prefix {
      deviate add {
            sonic-ext:field-transformer "bgp_gbl_afi_safi_addr_field_xfmr";
      }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:config/oc-bgp-ext:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:state/oc-bgp-ext:policy-name {
      deviate add {
            sonic-ext:field-name "policy";
      }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:config/oc-bgp-ext:backdoor {
      deviate add {
            sonic-ext:field-name "backdoor";
      }
    }

    deviation /oc-netinst:network-instances/oc-netinst:network-instance/oc-netinst:protocols/oc-netinst:protocol/oc-netinst:bgp/oc-netinst:global/oc-netinst:afi-safis/oc-netinst:afi-safi/oc-bgp-ext:network-config/oc-bgp-ext:network/oc-bgp-ext:state/oc-bgp-ext:backdoor {
      deviate add {
            sonic-ext:field-name "backdoor";
      }
    }

    deviation /oc-netinst:network-instances/oc-netinst:network-instance/oc-netinst:protocols/oc-netinst:protocol/oc-netinst:bgp/oc-netinst:global/oc-netinst:afi-safis/oc-netinst:afi-safi/oc-netinst:config/oc-bgp-ext:table-map-name {
      deviate add {
            sonic-ext:field-name "route_download_filter";
      }
    }

    deviation /oc-netinst:network-instances/oc-netinst:network-instance/oc-netinst:protocols/oc-netinst:protocol/oc-netinst:bgp/oc-netinst:global/oc-netinst:afi-safis/oc-netinst:afi-safi/oc-netinst:state/oc-bgp-ext:table-map-name {
      deviate add {
            sonic-ext:field-name "route_download_filter";
      }
    }

/* BGP Neighbors*/
    deviation /oc-netinst:network-instances/oc-netinst:network-instance/oc-netinst:protocols/oc-netinst:protocol/oc-netinst:bgp/oc-netinst:neighbors/oc-netinst:neighbor {
      deviate add {
        sonic-ext:table-transformer "bgp_nbr_tbl_xfmr";
        sonic-ext:key-transformer "bgp_nbr_tbl_key_xfmr";
      }
    }

    deviation /oc-netinst:network-instances/oc-netinst:network-instance/oc-netinst:protocols/oc-netinst:protocol/oc-netinst:bgp/oc-netinst:neighbors/oc-netinst:neighbor/oc-netinst:config/oc-netinst:neighbor-address {
      deviate add {
            sonic-ext:field-transformer "bgp_nbr_address_fld_xfmr";
      }
    }

    deviation /oc-netinst:network-instances/oc-netinst:network-instance/oc-netinst:protocols/oc-netinst:protocol/oc-netinst:bgp/oc-netinst:neighbors/oc-netinst:neighbor/oc-netinst:config/oc-netinst:enabled {
      deviate add {
            sonic-ext:field-name "admin_status";
      }
    }

    deviation /oc-netinst:network-instances/oc-netinst:network-instance/oc-netinst:protocols/oc-netinst:protocol/oc-netinst:bgp/oc-netinst:neighbors/oc-netinst:neighbor/oc-netinst:config/oc-netinst:peer-group {
      deviate add {
            sonic-ext:field-name "peer_group_name";
      }
    }

/* neighbor->ebgp-multihop */
    deviation /oc-netinst:network-instances/oc-netinst:network-instance/oc-netinst:protocols/oc-netinst:protocol/oc-netinst:bgp/oc-netinst:neighbors/oc-netinst:neighbor/oc-netinst:ebgp-multihop/oc-netinst:config/oc-netinst:multihop-ttl {
      deviate add {
            sonic-ext:field-name "ebgp_multihop_ttl";
      }
    }

    deviation /oc-netinst:network-instances/oc-netinst:network-instance/oc-netinst:protocols/oc-netinst:protocol/oc-netinst:bgp/oc-netinst:neighbors/oc-netinst:neighbor/oc-netinst:ebgp-multihop/oc-netinst:config/oc-netinst:enabled {
      deviate add {
            sonic-ext:field-name "ebgp_multihop";
      }
    }

/* neighbor->ebgp-multihop>state */
    deviation /oc-netinst:network-instances/oc-netinst:network-instance/oc-netinst:protocols/oc-netinst:protocol/oc-netinst:bgp/oc-netinst:neighbors/oc-netinst:neighbor/oc-netinst:ebgp-multihop/oc-netinst:state/oc-netinst:multihop-ttl {
      deviate add {
            sonic-ext:field-name "ebgp_multihop_ttl";
      }
    }

    deviation /oc-netinst:network-instances/oc-netinst:network-instance/oc-netinst:protocols/oc-netinst:protocol/oc-netinst:bgp/oc-netinst:neighbors/oc-netinst:neighbor/oc-netinst:ebgp-multihop/oc-netinst:state/oc-netinst:enabled {
      deviate add {
            sonic-ext:field-name "ebgp_multihop";
      }
    }

/* neighbor->timers->config */
/* neighbor->timers->config->minimum-advertisement-interval */
    deviation /oc-netinst:network-instances/oc-netinst:network-instance/oc-netinst:protocols/oc-netinst:protocol/oc-netinst:bgp/oc-netinst:neighbors/oc-netinst:neighbor/oc-netinst:timers/oc-netinst:config/oc-netinst:minimum-advertisement-interval {
      deviate add {
            sonic-ext:field-name "min_adv_interval";
      }
    }

/* neighbor->timers->config->connect-retry */
    deviation /oc-netinst:network-instances/oc-netinst:network-instance/oc-netinst:protocols/oc-netinst:protocol/oc-netinst:bgp/oc-netinst:neighbors/oc-netinst:neighbor/oc-netinst:timers/oc-netinst:config/oc-netinst:connect-retry {
      deviate add {
            sonic-ext:field-name "conn_retry";
      }
    }

/* neighbor->timers->config->hold-time */
    deviation /oc-netinst:network-instances/oc-netinst:network-instance/oc-netinst:protocols/oc-netinst:protocol/oc-netinst:bgp/oc-netinst:neighbors/oc-netinst:neighbor/oc-netinst:timers/oc-netinst:config/oc-netinst:hold-time {
      deviate add {
            sonic-ext:field-name "holdtime";
      }
    }

/* neighbor->timers->config->keepalive-interval */
    deviation /oc-netinst:network-instances/oc-netinst:network-instance/oc-netinst:protocols/oc-netinst:protocol/oc-netinst:bgp/oc-netinst:neighbors/oc-netinst:neighbor/oc-netinst:timers/oc-netinst:config/oc-netinst:keepalive-interval {
      deviate add {
            sonic-ext:field-name "keepalive";
      }
    }

/* neighbor->config */
/* neighbor->config->description */
    deviation /oc-netinst:network-instances/oc-netinst:network-instance/oc-netinst:protocols/oc-netinst:protocol/oc-netinst:bgp/oc-netinst:neighbors/oc-netinst:neighbor/oc-netinst:config/oc-netinst:description {
      deviate add {
            sonic-ext:field-name "name";
      }
    }

/* neighbor->config->peer-as */
    deviation /oc-netinst:network-instances/oc-netinst:network-instance/oc-netinst:protocols/oc-netinst:protocol/oc-netinst:bgp/oc-netinst:neighbors/oc-netinst:neighbor/oc-netinst:config/oc-netinst:peer-as {
      deviate add {
            sonic-ext:field-name "asn";
      }
    }

/* neighbor->config->peer-type */
    deviation /oc-netinst:network-instances/oc-netinst:network-instance/oc-netinst:protocols/oc-netinst:protocol/oc-netinst:bgp/oc-netinst:neighbors/oc-netinst:neighbor/oc-netinst:config/oc-netinst:peer-type {
      deviate add {
            sonic-ext:field-transformer "bgp_nbr_peer_type_fld_xfmr";
      }
    }

/* neighbor->config->local-as */
    deviation /oc-netinst:network-instances/oc-netinst:network-instance/oc-netinst:protocols/oc-netinst:protocol/oc-netinst:bgp/oc-netinst:neighbors/oc-netinst:neighbor/oc-netinst:config/oc-netinst:local-as {
      deviate add {
            sonic-ext:field-name "local_asn";
      }
    }

/* neighbor->transport->config */
/* neighbor->transport->config->passive-mode */
    deviation /oc-netinst:network-instances/oc-netinst:network-instance/oc-netinst:protocols/oc-netinst:protocol/oc-netinst:bgp/oc-netinst:neighbors/oc-netinst:neighbor/oc-netinst:transport/oc-netinst:config/oc-netinst:passive-mode {
      deviate add {
            sonic-ext:field-name "passive_mode";
      }
    }

/* neighbor->transport->config->local-address */
    deviation /oc-netinst:network-instances/oc-netinst:network-instance/oc-netinst:protocols/oc-netinst:protocol/oc-netinst:bgp/oc-netinst:neighbors/oc-netinst:neighbor/oc-netinst:transport/oc-netinst:config/oc-netinst:local-address {
      deviate add {
            sonic-ext:field-name "local_addr";
      }
    }

/* BGP NBR AFI SAFI */
    deviation /oc-netinst:network-instances/oc-netinst:network-instance/oc-netinst:protocols/oc-netinst:protocol/oc-netinst:bgp/oc-netinst:neighbors/oc-netinst:neighbor/oc-netinst:afi-safis/oc-netinst:afi-safi {
      deviate add {
        sonic-ext:table-name "BGP_NEIGHBOR_AF";
        sonic-ext:key-transformer "bgp_af_nbr_tbl_key_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:enabled {
      deviate add {
        sonic-ext:field-name "admin_status";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn {
      deviate add {
        sonic-ext:key-transformer "bgp_af_nbr_proto_tbl_key_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast {
      deviate add {
        sonic-ext:key-transformer "bgp_af_nbr_proto_tbl_key_xfmr";
      }
    }
    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast {
      deviate add {
        sonic-ext:key-transformer "bgp_af_nbr_proto_tbl_key_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:l2vpn-evpn/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-netinst:afi-safi-name {
      deviate add {
            sonic-ext:field-transformer "bgp_nbr_afi_safi_name_fld_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:config/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:config/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:import-policy {
      deviate add {
            sonic-ext:field-name "route_map_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:config/oc-netinst:export-policy {
      deviate add {
            sonic-ext:field-name "route_map_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:restart-timer {
      deviate add {
            sonic-ext:field-name "max_prefix_restart_interval";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:max-prefixes {
      deviate add {
            sonic-ext:field-name "max_prefix_limit";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:prevent-teardown {
      deviate add {
            sonic-ext:field-name "max_prefix_warning_only";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:prefix-limit/oc-netinst:state/oc-netinst:warning-threshold-pct {
      deviate add {
            sonic-ext:field-name "max_prefix_warning_threshold";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:state/oc-netinst:send-default-route {
      deviate add {
            sonic-ext:field-name "send_default_route";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:import-policy {
      deviate add {
            sonic-ext:field-name "route_map_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:apply-policy/oc-netinst:state/oc-netinst:export-policy {
      deviate add {
            sonic-ext:field-name "route_map_out";
      }
    }
/* BGP Extended attrs for NBR and Peer group */

    deviation /oc-netinst:network-instances/oc-netinst:network-instance/oc-netinst:protocols/oc-netinst:protocol/oc-netinst:bgp/oc-netinst:neighbors/oc-netinst:neighbor/oc-netinst:config/oc-bgp-ext:disable-ebgp-connected-route-check {
      deviate add {
        sonic-ext:field-name "disable_ebgp_connected_route_check";
      }
    }

    deviation /oc-netinst:network-instances/oc-netinst:network-instance/oc-netinst:protocols/oc-netinst:protocol/oc-netinst:bgp/oc-netinst:neighbors/oc-netinst:neighbor/oc-netinst:config/oc-bgp-ext:enforce-first-as {
      deviate add {
        sonic-ext:field-name "enforce_first_as";
      }
    }

    deviation /oc-netinst:network-instances/oc-netinst:network-instance/oc-netinst:protocols/oc-netinst:protocol/oc-netinst:bgp/oc-netinst:neighbors/oc-netinst:neighbor/oc-netinst:config/oc-bgp-ext:solo-peer {
      deviate add {
        sonic-ext:field-name "solo_peer";
      }
    }

    deviation /oc-netinst:network-instances/oc-netinst:network-instance/oc-netinst:protocols/oc-netinst:protocol/oc-netinst:bgp/oc-netinst:neighbors/oc-netinst:neighbor/oc-netinst:config/oc-bgp-ext:ttl-security-hops {
      deviate add {
        sonic-ext:field-name "ttl_security_hops";
      }
    }

    deviation /oc-netinst:network-instances/oc-netinst:network-instance/oc-netinst:protocols/oc-netinst:protocol/oc-netinst:bgp/oc-netinst:neighbors/oc-netinst:neighbor/oc-netinst:config/oc-bgp-ext:capability-extended-nexthop {
      deviate add {
        sonic-ext:field-name "capability_ext_nexthop";
      }
    }

    deviation /oc-netinst:network-instances/oc-netinst:network-instance/oc-netinst:protocols/oc-netinst:protocol/oc-netinst:bgp/oc-netinst:neighbors/oc-netinst:neighbor/oc-netinst:config/oc-bgp-ext:bfd {
      deviate add {
        sonic-ext:field-name "bfd";
      }
    }

    deviation /oc-netinst:network-instances/oc-netinst:network-instance/oc-netinst:protocols/oc-netinst:protocol/oc-netinst:bgp/oc-netinst:neighbors/oc-netinst:neighbor/oc-netinst:config/oc-bgp-ext:bfd-check-control-plane-failure {
      deviate add {
        sonic-ext:field-name "bfd_check_ctrl_plane_failure";
      }
    }


    deviation /oc-netinst:network-instances/oc-netinst:network-instance/oc-netinst:protocols/oc-netinst:protocol/oc-netinst:bgp/oc-netinst:neighbors/oc-netinst:neighbor/oc-netinst:config/oc-bgp-ext:capability-dynamic {
      deviate add {
        sonic-ext:field-name "capability_dynamic";
      }
    }

    deviation /oc-netinst:network-instances/oc-netinst:network-instance/oc-netinst:protocols/oc-netinst:protocol/oc-netinst:bgp/oc-netinst:neighbors/oc-netinst:neighbor/oc-netinst:config/oc-bgp-ext:dont-negotiate-capability {
      deviate add {
        sonic-ext:field-name "dont_negotiate_capability";
      }
    }

    deviation /oc-netinst:network-instances/oc-netinst:network-instance/oc-netinst:protocols/oc-netinst:protocol/oc-netinst:bgp/oc-netinst:neighbors/oc-netinst:neighbor/oc-netinst:config/oc-bgp-ext:enforce-multihop {
      deviate add {
        sonic-ext:field-name "enforce_multihop";
      }
    }

    deviation /oc-netinst:network-instances/oc-netinst:network-instance/oc-netinst:protocols/oc-netinst:protocol/oc-netinst:bgp/oc-netinst:neighbors/oc-netinst:neighbor/oc-netinst:config/oc-bgp-ext:override-capability {
      deviate add {
        sonic-ext:field-name "override_capability";
      }
    }

    deviation /oc-netinst:network-instances/oc-netinst:network-instance/oc-netinst:protocols/oc-netinst:protocol/oc-netinst:bgp/oc-netinst:neighbors/oc-netinst:neighbor/oc-netinst:config/oc-bgp-ext:peer-port {
      deviate add {
        sonic-ext:field-name "peer_port";
      }
    }

    deviation /oc-netinst:network-instances/oc-netinst:network-instance/oc-netinst:protocols/oc-netinst:protocol/oc-netinst:bgp/oc-netinst:neighbors/oc-netinst:neighbor/oc-netinst:config/oc-bgp-ext:shutdown-message {
      deviate add {
        sonic-ext:field-name "shutdown_message";
      }
    }

    deviation /oc-netinst:network-instances/oc-netinst:network-instance/oc-netinst:protocols/oc-netinst:protocol/oc-netinst:bgp/oc-netinst:neighbors/oc-netinst:neighbor/oc-netinst:config/oc-bgp-ext:strict-capability-match {
      deviate add {
        sonic-ext:field-name "strict_capability_match";
      }
    }

    deviation /oc-netinst:network-instances/oc-netinst:network-instance/oc-netinst:protocols/oc-netinst:protocol/oc-netinst:bgp/oc-netinst:neighbors/oc-netinst:neighbor/oc-netinst:config/oc-bgp-ext:local-as-no-prepend {
      deviate add {
        sonic-ext:field-name "local_as_no_prepend";
      }
    }

    deviation /oc-netinst:network-instances/oc-netinst:network-instance/oc-netinst:protocols/oc-netinst:protocol/oc-netinst:bgp/oc-netinst:neighbors/oc-netinst:neighbor/oc-netinst:config/oc-bgp-ext:local-as-replace-as {
      deviate add {
        sonic-ext:field-name "local_as_replace_as";
      }
    }

    deviation /oc-netinst:network-instances/oc-netinst:network-instance/oc-netinst:protocols/oc-netinst:protocol/oc-netinst:bgp/oc-netinst:peer-groups/oc-netinst:peer-group/oc-netinst:config/oc-bgp-ext:disable-ebgp-connected-route-check {
      deviate add {
        sonic-ext:field-name "disable_ebgp_connected_route_check";
      }
    }

    deviation /oc-netinst:network-instances/oc-netinst:network-instance/oc-netinst:protocols/oc-netinst:protocol/oc-netinst:bgp/oc-netinst:peer-groups/oc-netinst:peer-group/oc-netinst:config/oc-bgp-ext:enforce-first-as {
      deviate add {
        sonic-ext:field-name "enforce_first_as";
      }
    }

    deviation /oc-netinst:network-instances/oc-netinst:network-instance/oc-netinst:protocols/oc-netinst:protocol/oc-netinst:bgp/oc-netinst:peer-groups/oc-netinst:peer-group/oc-netinst:config/oc-bgp-ext:solo-peer {
      deviate add {
        sonic-ext:field-name "solo_peer";
      }
    }

    deviation /oc-netinst:network-instances/oc-netinst:network-instance/oc-netinst:protocols/oc-netinst:protocol/oc-netinst:bgp/oc-netinst:peer-groups/oc-netinst:peer-group/oc-netinst:config/oc-bgp-ext:ttl-security-hops {
      deviate add {
        sonic-ext:field-name "ttl_security_hops";
      }
    }

    deviation /oc-netinst:network-instances/oc-netinst:network-instance/oc-netinst:protocols/oc-netinst:protocol/oc-netinst:bgp/oc-netinst:peer-groups/oc-netinst:peer-group/oc-netinst:config/oc-bgp-ext:capability-extended-nexthop {
      deviate add {
        sonic-ext:field-name "capability_ext_nexthop";
      }
    }

    deviation /oc-netinst:network-instances/oc-netinst:network-instance/oc-netinst:protocols/oc-netinst:protocol/oc-netinst:bgp/oc-netinst:peer-groups/oc-netinst:peer-group/oc-netinst:config/oc-bgp-ext:bfd {
      deviate add {
        sonic-ext:field-name "bfd";
      }
    }

    deviation /oc-netinst:network-instances/oc-netinst:network-instance/oc-netinst:protocols/oc-netinst:protocol/oc-netinst:bgp/oc-netinst:peer-groups/oc-netinst:peer-group/oc-netinst:config/oc-bgp-ext:bfd-check-control-plane-failure {
      deviate add {
        sonic-ext:field-name "bfd_check_ctrl_plane_failure";
      }
    }

    deviation /oc-netinst:network-instances/oc-netinst:network-instance/oc-netinst:protocols/oc-netinst:protocol/oc-netinst:bgp/oc-netinst:peer-groups/oc-netinst:peer-group/oc-netinst:state/oc-bgp-ext:disable-ebgp-connected-route-check {
      deviate add {
        sonic-ext:field-name "disable_ebgp_connected_route_check";
      }
    }

    deviation /oc-netinst:network-instances/oc-netinst:network-instance/oc-netinst:protocols/oc-netinst:protocol/oc-netinst:bgp/oc-netinst:peer-groups/oc-netinst:peer-group/oc-netinst:state/oc-bgp-ext:enforce-first-as {
      deviate add {
        sonic-ext:field-name "enforce_first_as";
      }
    }

    deviation /oc-netinst:network-instances/oc-netinst:network-instance/oc-netinst:protocols/oc-netinst:protocol/oc-netinst:bgp/oc-netinst:peer-groups/oc-netinst:peer-group/oc-netinst:state/oc-bgp-ext:solo-peer {
      deviate add {
        sonic-ext:field-name "solo_peer";
      }
    }

    deviation /oc-netinst:network-instances/oc-netinst:network-instance/oc-netinst:protocols/oc-netinst:protocol/oc-netinst:bgp/oc-netinst:peer-groups/oc-netinst:peer-group/oc-netinst:state/oc-bgp-ext:ttl-security-hops {
      deviate add {
        sonic-ext:field-name "ttl_security_hops";
      }
    }

    deviation /oc-netinst:network-instances/oc-netinst:network-instance/oc-netinst:protocols/oc-netinst:protocol/oc-netinst:bgp/oc-netinst:peer-groups/oc-netinst:peer-group/oc-netinst:state/oc-bgp-ext:capability-extended-nexthop {
      deviate add {
        sonic-ext:field-name "capability_ext_nexthop";
      }
    }

    deviation /oc-netinst:network-instances/oc-netinst:network-instance/oc-netinst:protocols/oc-netinst:protocol/oc-netinst:bgp/oc-netinst:peer-groups/oc-netinst:peer-group/oc-netinst:state/oc-bgp-ext:bfd {
      deviate add {
        sonic-ext:field-name "bfd";
      }
    }

    deviation /oc-netinst:network-instances/oc-netinst:network-instance/oc-netinst:protocols/oc-netinst:protocol/oc-netinst:bgp/oc-netinst:peer-groups/oc-netinst:peer-group/oc-netinst:state/oc-bgp-ext:bfd-check-control-plane-failure {
      deviate add {
        sonic-ext:field-name "bfd_check_ctrl_plane_failure";
      }
    }

    deviation /oc-netinst:network-instances/oc-netinst:network-instance/oc-netinst:protocols/oc-netinst:protocol/oc-netinst:bgp/oc-netinst:peer-groups/oc-netinst:peer-group/oc-netinst:config/oc-bgp-ext:capability-dynamic {
      deviate add {
        sonic-ext:field-name "capability_dynamic";
      }
    }

    deviation /oc-netinst:network-instances/oc-netinst:network-instance/oc-netinst:protocols/oc-netinst:protocol/oc-netinst:bgp/oc-netinst:peer-groups/oc-netinst:peer-group/oc-netinst:config/oc-bgp-ext:dont-negotiate-capability {
      deviate add {
        sonic-ext:field-name "dont_negotiate_capability";
      }
    }

    deviation /oc-netinst:network-instances/oc-netinst:network-instance/oc-netinst:protocols/oc-netinst:protocol/oc-netinst:bgp/oc-netinst:peer-groups/oc-netinst:peer-group/oc-netinst:config/oc-bgp-ext:enforce-multihop {
      deviate add {
        sonic-ext:field-name "enforce_multihop";
      }
    }

    deviation /oc-netinst:network-instances/oc-netinst:network-instance/oc-netinst:protocols/oc-netinst:protocol/oc-netinst:bgp/oc-netinst:peer-groups/oc-netinst:peer-group/oc-netinst:config/oc-bgp-ext:override-capability {
      deviate add {
        sonic-ext:field-name "override_capability";
      }
    }

    deviation /oc-netinst:network-instances/oc-netinst:network-instance/oc-netinst:protocols/oc-netinst:protocol/oc-netinst:bgp/oc-netinst:peer-groups/oc-netinst:peer-group/oc-netinst:config/oc-bgp-ext:peer-port {
      deviate add {
        sonic-ext:field-name "peer_port";
      }
    }

    deviation /oc-netinst:network-instances/oc-netinst:network-instance/oc-netinst:protocols/oc-netinst:protocol/oc-netinst:bgp/oc-netinst:peer-groups/oc-netinst:peer-group/oc-netinst:config/oc-bgp-ext:shutdown-message {
      deviate add {
        sonic-ext:field-name "shutdown_message";
      }
    }

    deviation /oc-netinst:network-instances/oc-netinst:network-instance/oc-netinst:protocols/oc-netinst:protocol/oc-netinst:bgp/oc-netinst:peer-groups/oc-netinst:peer-group/oc-netinst:config/oc-bgp-ext:strict-capability-match {
      deviate add {
        sonic-ext:field-name "strict_capability_match";
      }
    }

    deviation /oc-netinst:network-instances/oc-netinst:network-instance/oc-netinst:protocols/oc-netinst:protocol/oc-netinst:bgp/oc-netinst:peer-groups/oc-netinst:peer-group/oc-netinst:config/oc-bgp-ext:local-as-no-prepend {
      deviate add {
        sonic-ext:field-name "local_as_no_prepend";
      }
    }

    deviation /oc-netinst:network-instances/oc-netinst:network-instance/oc-netinst:protocols/oc-netinst:protocol/oc-netinst:bgp/oc-netinst:peer-groups/oc-netinst:peer-group/oc-netinst:config/oc-bgp-ext:local-as-replace-as {
      deviate add {
        sonic-ext:field-name "local_as_replace_as";
      }
    }


    deviation /oc-netinst:network-instances/oc-netinst:network-instance/oc-netinst:protocols/oc-netinst:protocol/oc-netinst:bgp/oc-netinst:peer-groups/oc-netinst:peer-group/oc-netinst:state/oc-bgp-ext:capability-dynamic {
      deviate add {
        sonic-ext:field-name "capability_dynamic";
      }
    }

    deviation /oc-netinst:network-instances/oc-netinst:network-instance/oc-netinst:protocols/oc-netinst:protocol/oc-netinst:bgp/oc-netinst:peer-groups/oc-netinst:peer-group/oc-netinst:state/oc-bgp-ext:dont-negotiate-capability {
      deviate add {
        sonic-ext:field-name "dont_negotiate_capability";
      }
    }

    deviation /oc-netinst:network-instances/oc-netinst:network-instance/oc-netinst:protocols/oc-netinst:protocol/oc-netinst:bgp/oc-netinst:peer-groups/oc-netinst:peer-group/oc-netinst:state/oc-bgp-ext:enforce-multihop {
      deviate add {
        sonic-ext:field-name "enforce_multihop";
      }
    }

    deviation /oc-netinst:network-instances/oc-netinst:network-instance/oc-netinst:protocols/oc-netinst:protocol/oc-netinst:bgp/oc-netinst:peer-groups/oc-netinst:peer-group/oc-netinst:state/oc-bgp-ext:override-capability {
      deviate add {
        sonic-ext:field-name "override_capability";
      }
    }

    deviation /oc-netinst:network-instances/oc-netinst:network-instance/oc-netinst:protocols/oc-netinst:protocol/oc-netinst:bgp/oc-netinst:peer-groups/oc-netinst:peer-group/oc-netinst:state/oc-bgp-ext:peer-port {
      deviate add {
        sonic-ext:field-name "peer_port";
      }
    }

    deviation /oc-netinst:network-instances/oc-netinst:network-instance/oc-netinst:protocols/oc-netinst:protocol/oc-netinst:bgp/oc-netinst:peer-groups/oc-netinst:peer-group/oc-netinst:state/oc-bgp-ext:shutdown-message {
      deviate add {
        sonic-ext:field-name "shutdown_message";
      }
    }

    deviation /oc-netinst:network-instances/oc-netinst:network-instance/oc-netinst:protocols/oc-netinst:protocol/oc-netinst:bgp/oc-netinst:peer-groups/oc-netinst:peer-group/oc-netinst:state/oc-bgp-ext:strict-capability-match {
      deviate add {
        sonic-ext:field-name "strict_capability_match";
      }
    }

    deviation /oc-netinst:network-instances/oc-netinst:network-instance/oc-netinst:protocols/oc-netinst:protocol/oc-netinst:bgp/oc-netinst:peer-groups/oc-netinst:peer-group/oc-netinst:state/oc-bgp-ext:local-as-no-prepend {
      deviate add {
        sonic-ext:field-name "local_as_no_prepend";
      }
    }

    deviation /oc-netinst:network-instances/oc-netinst:network-instance/oc-netinst:protocols/oc-netinst:protocol/oc-netinst:bgp/oc-netinst:peer-groups/oc-netinst:peer-group/oc-netinst:state/oc-bgp-ext:local-as-replace-as {
      deviate add {
        sonic-ext:field-name "local_as_replace_as";
      }
    }



/* BGP Extended attrs for NBR and Peer group AFI_SAFI */

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:soft-reconfiguration-in {
      deviate add {
        sonic-ext:field-name "soft_reconfiguration_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:unsuppress-map-name {
      deviate add {
        sonic-ext:field-name "unsuppress_map_name";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:weight {
      deviate add {
        sonic-ext:field-name "weight";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:as-override {
      deviate add {
        sonic-ext:field-name "as_override";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:send-community {
      deviate add {
        sonic-ext:field-transformer "bgp_nbr_community_type_fld_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:route-reflector-client {
      deviate add {
        sonic-ext:field-name "rrclient";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:config/oc-bgp-ext:route-server-client {
      deviate add {
        sonic-ext:field-name "route_server_client";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:config/oc-bgp-ext:tx-add-paths {
      deviate add {
        sonic-ext:field-transformer "bgp_nbr_tx_add_paths_fld_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:add-paths/oc-netinst:state/oc-bgp-ext:tx-add-paths {
      deviate add {
        sonic-ext:field-transformer "bgp_nbr_tx_add_paths_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:config/oc-bgp-ext:tx-add-paths {
      deviate add {
        sonic-ext:field-transformer "bgp_pgrp_tx_add_paths_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:add-paths/oc-netinst:state/oc-bgp-ext:tx-add-paths {
      deviate add {
        sonic-ext:field-transformer "bgp_pgrp_tx_add_paths_fld_xfmr";
      }
    }


    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:soft-reconfiguration-in {
      deviate add {
        sonic-ext:field-name "soft_reconfiguration_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:unsuppress-map-name {
      deviate add {
        sonic-ext:field-name "unsuppress_map_name";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:weight {
      deviate add {
        sonic-ext:field-name "weight";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:as-override {
      deviate add {
        sonic-ext:field-name "as_override";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:send-community {
      deviate add {
        sonic-ext:field-transformer "bgp_pgrp_community_type_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:route-reflector-client {
      deviate add {
        sonic-ext:field-name "rrclient";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:config/oc-bgp-ext:route-server-client {
      deviate add {
        sonic-ext:field-name "route_server_client";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:soft-reconfiguration-in {
      deviate add {
        sonic-ext:field-name "soft_reconfiguration_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:unsuppress-map-name {
      deviate add {
        sonic-ext:field-name "unsuppress_map_name";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:weight {
      deviate add {
        sonic-ext:field-name "weight";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:as-override {
      deviate add {
        sonic-ext:field-name "as_override";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:send-community {
      deviate add {
        sonic-ext:field-transformer "bgp_pgrp_community_type_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:route-reflector-client {
      deviate add {
        sonic-ext:field-name "rrclient";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:state/oc-bgp-ext:route-server-client {
      deviate add {
        sonic-ext:field-name "route_server_client";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:allow-own-as/oc-bgp-ext:config/oc-bgp-ext:enabled {
      deviate add {
        sonic-ext:field-name "allow_as_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:allow-own-as/oc-bgp-ext:config/oc-bgp-ext:as-count {
      deviate add {
        sonic-ext:field-name "allow_as_count";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:allow-own-as/oc-bgp-ext:config/oc-bgp-ext:origin {
      deviate add {
        sonic-ext:field-name "allow_as_origin";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:allow-own-as/oc-bgp-ext:state/oc-bgp-ext:enabled {
      deviate add {
        sonic-ext:field-name "allow_as_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:allow-own-as/oc-bgp-ext:state/oc-bgp-ext:as-count {
      deviate add {
        sonic-ext:field-name "allow_as_count";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:allow-own-as/oc-bgp-ext:state/oc-bgp-ext:origin {
      deviate add {
        sonic-ext:field-name "allow_as_origin";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:attribute-unchanged/oc-bgp-ext:config/oc-bgp-ext:as-path {
      deviate add {
        sonic-ext:field-name "unchanged_as_path";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:attribute-unchanged/oc-bgp-ext:config/oc-bgp-ext:med {
      deviate add {
        sonic-ext:field-name "unchanged_med";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:attribute-unchanged/oc-bgp-ext:config/oc-bgp-ext:next-hop {
      deviate add {
        sonic-ext:field-name "unchanged_nexthop";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:attribute-unchanged/oc-bgp-ext:state/oc-bgp-ext:as-path {
      deviate add {
        sonic-ext:field-name "unchanged_as_path";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:attribute-unchanged/oc-bgp-ext:state/oc-bgp-ext:med {
      deviate add {
        sonic-ext:field-name "unchanged_med";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:attribute-unchanged/oc-bgp-ext:state/oc-bgp-ext:next-hop {
      deviate add {
        sonic-ext:field-name "unchanged_nexthop";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:filter-list/oc-bgp-ext:config/oc-bgp-ext:import-policy {
      deviate add {
        sonic-ext:field-name "filter_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:filter-list/oc-bgp-ext:config/oc-bgp-ext:export-policy {
      deviate add {
        sonic-ext:field-name "filter_list_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:filter-list/oc-bgp-ext:state/oc-bgp-ext:import-policy {
      deviate add {
        sonic-ext:field-name "filter_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:filter-list/oc-bgp-ext:state/oc-bgp-ext:export-policy {
      deviate add {
        sonic-ext:field-name "filter_list_out";
      }
    }


    deviation /oc-netinst:network-instances/oc-netinst:network-instance/oc-netinst:protocols/oc-netinst:protocol/oc-netinst:bgp/oc-netinst:neighbors/oc-netinst:neighbor/oc-netinst:afi-safis/oc-netinst:afi-safi/oc-bgp-ext:next-hop-self/oc-bgp-ext:config/oc-bgp-ext:enabled {
      deviate add {
        sonic-ext:field-name "nhself";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:next-hop-self/oc-bgp-ext:config/oc-bgp-ext:force {
      deviate add {
        sonic-ext:field-name "nexthop_self_force";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:next-hop-self/oc-bgp-ext:state/oc-bgp-ext:enabled {
      deviate add {
        sonic-ext:field-name "nhself";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:next-hop-self/oc-bgp-ext:state/oc-bgp-ext:force {
      deviate add {
        sonic-ext:field-name "nexthop_self_force";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:prefix-list/oc-bgp-ext:config/oc-bgp-ext:import-policy {
      deviate add {
        sonic-ext:field-name "prefix_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:prefix-list/oc-bgp-ext:config/oc-bgp-ext:export-policy {
      deviate add {
        sonic-ext:field-name "prefix_list_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:prefix-list/oc-bgp-ext:state/oc-bgp-ext:import-policy {
      deviate add {
        sonic-ext:field-name "prefix_list_in";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:prefix-list/oc-bgp-ext:state/oc-bgp-ext:export-policy {
      deviate add {
        sonic-ext:field-name "prefix_list_out";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:remove-private-as/oc-bgp-ext:config/oc-bgp-ext:enabled {
      deviate add {
        sonic-ext:field-name "remove_private_as_enabled";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:remove-private-as/oc-bgp-ext:config/oc-bgp-ext:all {
      deviate add {
        sonic-ext:field-name "remove_private_as_all";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:remove-private-as/oc-bgp-ext:config/oc-bgp-ext:replace-as {
      deviate add {
        sonic-ext:field-name "replace_private_as";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:remove-private-as/oc-bgp-ext:state/oc-bgp-ext:enabled {
      deviate add {
        sonic-ext:field-name "remove_private_as_enabled";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:remove-private-as/oc-bgp-ext:state/oc-bgp-ext:all {
      deviate add {
        sonic-ext:field-name "remove_private_as_all";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:remove-private-as/oc-bgp-ext:state/oc-bgp-ext:replace-as {
      deviate add {
        sonic-ext:field-name "replace_private_as";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:capability-orf/oc-bgp-ext:config/oc-bgp-ext:orf-type {
      deviate add {
        sonic-ext:field-transformer "bgp_nbr_orf_type_fld_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-bgp-ext:capability-orf/oc-bgp-ext:state/oc-bgp-ext:orf-type {
      deviate add {
        sonic-ext:field-transformer "bgp_nbr_orf_type_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:allow-own-as/oc-bgp-ext:config/oc-bgp-ext:enabled {
      deviate add {
        sonic-ext:field-name "allow_as_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:allow-own-as/oc-bgp-ext:config/oc-bgp-ext:as-count {
      deviate add {
        sonic-ext:field-name "allow_as_count";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:allow-own-as/oc-bgp-ext:config/oc-bgp-ext:origin {
      deviate add {
        sonic-ext:field-name "allow_as_origin";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:allow-own-as/oc-bgp-ext:state/oc-bgp-ext:enabled {
      deviate add {
        sonic-ext:field-name "allow_as_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:allow-own-as/oc-bgp-ext:state/oc-bgp-ext:as-count {
      deviate add {
        sonic-ext:field-name "allow_as_count";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:allow-own-as/oc-bgp-ext:state/oc-bgp-ext:origin {
      deviate add {
        sonic-ext:field-name "allow_as_origin";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:attribute-unchanged/oc-bgp-ext:config/oc-bgp-ext:as-path {
      deviate add {
        sonic-ext:field-name "unchanged_as_path";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:attribute-unchanged/oc-bgp-ext:config/oc-bgp-ext:med {
      deviate add {
        sonic-ext:field-name "unchanged_med";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:attribute-unchanged/oc-bgp-ext:config/oc-bgp-ext:next-hop {
      deviate add {
        sonic-ext:field-name "unchanged_nexthop";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:attribute-unchanged/oc-bgp-ext:state/oc-bgp-ext:as-path {
      deviate add {
        sonic-ext:field-name "unchanged_as_path";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:attribute-unchanged/oc-bgp-ext:state/oc-bgp-ext:med {
      deviate add {
        sonic-ext:field-name "unchanged_med";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:attribute-unchanged/oc-bgp-ext:state/oc-bgp-ext:next-hop {
      deviate add {
        sonic-ext:field-name "unchanged_nexthop";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:filter-list/oc-bgp-ext:config/oc-bgp-ext:import-policy {
      deviate add {
        sonic-ext:field-name "filter_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:filter-list/oc-bgp-ext:config/oc-bgp-ext:export-policy {
      deviate add {
        sonic-ext:field-name "filter_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:filter-list/oc-bgp-ext:state/oc-bgp-ext:import-policy {
      deviate add {
        sonic-ext:field-name "filter_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:filter-list/oc-bgp-ext:state/oc-bgp-ext:export-policy {
      deviate add {
        sonic-ext:field-name "filter_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:next-hop-self/oc-bgp-ext:config/oc-bgp-ext:enabled {
      deviate add {
        sonic-ext:field-name "nhself";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:next-hop-self/oc-bgp-ext:config/oc-bgp-ext:force {
      deviate add {
        sonic-ext:field-name "nexthop_self_force";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:next-hop-self/oc-bgp-ext:state/oc-bgp-ext:enabled {
      deviate add {
        sonic-ext:field-name "nhself";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:next-hop-self/oc-bgp-ext:state/oc-bgp-ext:force {
      deviate add {
        sonic-ext:field-name "nexthop_self_force";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:prefix-list/oc-bgp-ext:config/oc-bgp-ext:import-policy {
      deviate add {
        sonic-ext:field-name "prefix_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:prefix-list/oc-bgp-ext:config/oc-bgp-ext:export-policy {
      deviate add {
        sonic-ext:field-name "prefix_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:prefix-list/oc-bgp-ext:state/oc-bgp-ext:import-policy {
      deviate add {
        sonic-ext:field-name "prefix_list_in";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:prefix-list/oc-bgp-ext:state/oc-bgp-ext:export-policy {
      deviate add {
        sonic-ext:field-name "prefix_list_out";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:remove-private-as/oc-bgp-ext:config/oc-bgp-ext:enabled {
      deviate add {
        sonic-ext:field-name "remove_private_as_enabled";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:remove-private-as/oc-bgp-ext:config/oc-bgp-ext:all {
      deviate add {
        sonic-ext:field-name "remove_private_as_all";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:remove-private-as/oc-bgp-ext:config/oc-bgp-ext:replace-as {
      deviate add {
        sonic-ext:field-name "replace_private_as";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:remove-private-as/oc-bgp-ext:state/oc-bgp-ext:enabled {
      deviate add {
        sonic-ext:field-name "remove_private_as_enabled";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:remove-private-as/oc-bgp-ext:state/oc-bgp-ext:all {
      deviate add {
        sonic-ext:field-name "remove_private_as_all";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:remove-private-as/oc-bgp-ext:state/oc-bgp-ext:replace-as {
      deviate add {
        sonic-ext:field-name "replace_private_as";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:capability-orf/oc-bgp-ext:config/oc-bgp-ext:orf-type {
      deviate add {
        sonic-ext:field-transformer "bgp_pgrp_orf_type_fld_xfmr";
      }
    }

    deviation /oc-netinst:network-instances/oc-netinst:network-instance/oc-netinst:protocols/oc-netinst:protocol/oc-netinst:bgp/oc-netinst:peer-groups/oc-netinst:peer-group/oc-netinst:afi-safis/oc-netinst:afi-safi/oc-bgp-ext:capability-orf/oc-bgp-ext:state/oc-bgp-ext:orf-type {
      deviate add {
        sonic-ext:field-transformer "bgp_pgrp_orf_type_fld_xfmr";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:config/oc-bgp-ext:default-policy-name {
      deviate add {
        sonic-ext:field-name "default_rmap";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv4-unicast/oc-netinst:state/oc-bgp-ext:default-policy-name {
      deviate add {
        sonic-ext:field-name "default_rmap";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:config/oc-bgp-ext:default-policy-name {
      deviate add {
        sonic-ext:field-name "default_rmap";
      }
    }

    deviation /oc-netinst:network-instances/oc-netinst:network-instance/oc-netinst:protocols/oc-netinst:protocol/oc-netinst:bgp/oc-netinst:neighbors/oc-netinst:neighbor/oc-netinst:afi-safis/oc-netinst:afi-safi/oc-netinst:ipv6-unicast/oc-netinst:state/oc-bgp-ext:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:config/oc-bgp-ext:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv4-unicast/oc-netinst:state/oc-bgp-ext:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:config/oc-bgp-ext:default-policy-name {
      deviate add {
        sonic-ext:field-name "default_rmap";
      }
    }

    deviation /oc-netinst:network-instances/oc-netinst:network-instance/oc-netinst:protocols/oc-netinst:protocol/oc-netinst:bgp/oc-netinst:peer-groups/oc-netinst:peer-group/oc-netinst:afi-safis/oc-netinst:afi-safi/oc-netinst:ipv6-unicast/oc-netinst:state/oc-bgp-ext:default-policy-name {
      deviate add {
        sonic-ext:field-name "default_rmap";
      }
    }
     deviation /oc-netinst:network-instances/oc-netinst:network-instance/oc-netinst:afts/oc-netinst:ipv4-unicast {
      deviate add {
        sonic-ext:subtree-transformer "ipv4_route_get_xfmr";
      }
     }

     deviation /oc-netinst:network-instances/oc-netinst:network-instance/oc-netinst:afts/oc-netinst:ipv6-unicast {
      deviate add {
        sonic-ext:subtree-transformer "ipv6_route_get_xfmr";
      }
     }

    deviation /oc-netinst:network-instances/oc-netinst:network-instance/oc-netinst:protocols/oc-netinst:protocol/oc-netinst-deviation:igmp-snooping/oc-netinst-deviation:interfaces/oc-netinst-deviation:interface/oc-netinst-deviation:config
    {
      deviate add {
            sonic-ext:table-name "CFG_L2MC_TABLE";
            sonic-ext:key-transformer "igmp_snooping_key_xfmr";    
      }
    }

    deviation /oc-netinst:network-instances/oc-netinst:network-instance/oc-netinst:protocols/oc-netinst:protocol/oc-netinst-deviation:igmp-snooping/oc-netinst-deviation:interfaces/oc-netinst-deviation:interface/oc-netinst-deviation:state
    {
      deviate add {
            sonic-ext:table-name "CFG_L2MC_TABLE";
            sonic-ext:key-transformer "igmp_snooping_key_xfmr";    
      }
    }

    deviation /oc-netinst:network-instances/oc-netinst:network-instance/oc-netinst:protocols/oc-netinst:protocol/oc-netinst-deviation:igmp-snooping/oc-netinst-deviation:interfaces/oc-netinst-deviation:interface/oc-netinst-deviation:config/oc-netinst-deviation:mrouter-interface
    {
      deviate add {
            sonic-ext:table-name "CFG_L2MC_MROUTER_TABLE";
            sonic-ext:key-transformer "igmp_snooping_mrouter_config_key_xfmr";    
      }
    }

    deviation /oc-netinst:network-instances/oc-netinst:network-instance/oc-netinst:protocols/oc-netinst:protocol/oc-netinst-deviation:igmp-snooping/oc-netinst-deviation:interfaces/oc-netinst-deviation:interface/oc-netinst-deviation:state/oc-netinst-deviation:mrouter-interface
    {
      deviate add {
      			sonic-ext:db-name "APPL_DB";
            sonic-ext:table-name "APP_L2MC_MROUTER_TABLE";
            sonic-ext:key-transformer "igmp_snooping_mrouter_state_key_xfmr";    
      }
    }

    deviation /oc-netinst:network-instances/oc-netinst:network-instance/oc-netinst:protocols/oc-netinst:protocol/oc-netinst-deviation:igmp-snooping/oc-netinst-deviation:interfaces/oc-netinst-deviation:interface/oc-netinst-deviation:config/oc-netinst-deviation:static-multicast-group 
    {
      deviate add {
            sonic-ext:table-name "CFG_L2MC_STATIC_GROUP_TABLE";
            sonic-ext:key-transformer "igmp_snooping_static_group_config_key_xfmr";    
      }
    }

    deviation /oc-netinst:network-instances/oc-netinst:network-instance/oc-netinst:protocols/oc-netinst:protocol/oc-netinst-deviation:igmp-snooping/oc-netinst-deviation:interfaces/oc-netinst-deviation:interface/oc-netinst-deviation:state/oc-netinst-deviation:static-multicast-group 
    {
      deviate add {
      			sonic-ext:db-name "APPL_DB";
            sonic-ext:table-name "APP_L2MC_MEMBER_TABLE";
            sonic-ext:key-transformer "igmp_snooping_static_member_state_key_xfmr";
      }
    }
    
    deviation /oc-netinst:network-instances/oc-netinst:network-instance/oc-netinst:protocols/oc-netinst:protocol/oc-netinst-deviation:igmp-snooping {
			deviate add {
				sonic-ext:subtree-transformer "igmp_snooping_subtree_xfmr";
			}    
    }  
    
    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni {
      deviate add {
        sonic-ext:table-name "BGP_GLOBALS_EVPN_VNI";
        sonic-ext:key-transformer "bgp_evpn_vni_key_xfmr";
      }
    } 

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:config/oc-bgp-evpn-ext:vni-number {
      deviate add {
            sonic-ext:field-transformer "bgp_vni_number_fld_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vpn-target {
      deviate add {
        sonic-ext:table-name "BGP_GLOBALS_EVPN_RT";
        sonic-ext:key-transformer "bgp_evpn_rt_key_xfmr";
      }
    } 

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vpn-target/oc-bgp-evpn-ext:route-target {
      deviate add {
            sonic-ext:field-transformer "bgp_rt_fld_xfmr";
      }
    }

    /*deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vpn-target/oc-bgp-evpn-ext:route-target-type {
      deviate add {
        sonic-ext:field-transformer "bgp_rt_type_fld_xfmr";
      }
    }*/

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:vpn-target {
      deviate add {
        sonic-ext:table-name "BGP_GLOBALS_EVPN_VNI_RT";
        sonic-ext:key-transformer "bgp_evpn_vni_rt_key_xfmr";
      }
    } 

    /*deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:vpn-target/oc-bgp-evpn-ext:route-target {
      deviate add {
            sonic-ext:field-transformer "bgp_rt_fld_xfmr";
      }
    }*/

    /*deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:vpn-target/oc-bgp-evpn-ext:route-target-type {
      deviate add {
        sonic-ext:field-transformer "bgp_rt_type_fld_xfmr";
      }
    }*/

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:default-originate/oc-bgp-evpn-ext:ipv4 {
      deviate add {
        sonic-ext:field-name "default-originate-ipv4";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:default-originate/oc-bgp-evpn-ext:ipv6 {
      deviate add {
        sonic-ext:field-name "default-originate-ipv6";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:advertise-list {
      deviate add {
            sonic-ext:field-transformer "bgp_advertise_fld_xfmr";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:enabled {
      deviate add {
        sonic-ext:field-name "dad-enabled";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:max-moves {
      deviate add {
        sonic-ext:field-name "dad-max-moves";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:time {
      deviate add {
        sonic-ext:field-name "dad-time";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:dup-addr-detection/oc-bgp-evpn-ext:freeze {
      deviate add {
        sonic-ext:field-name "dad-freeze";
      }
    }

    deviation /oc-netinst:network-instances/oc-netinst:network-instance/oc-netinst:protocols/oc-netinst:protocol/oc-netinst:bgp/oc-netinst:global/oc-netinst:afi-safis/oc-netinst:afi-safi/oc-netinst:l2vpn-evpn/oc-bgp-evpn-ext:vnis/oc-bgp-evpn-ext:vni/oc-bgp-evpn-ext:state {
      deviate add {
            sonic-ext:subtree-transformer "bgp_evpn_vni_state_xfmr";
      }
    }
	

    deviation /oc-netinst:network-instances/oc-netinst:network-instance/oc-netinst-ext:global-sag {
      deviate add {
        sonic-ext:table-name "SAG_GLOBAL";
        sonic-ext:key-transformer "sag_global_key_xfmr";		
      }
    }

    deviation /oc-netinst:network-instances/oc-netinst:network-instance/oc-netinst-ext:global-sag/oc-netinst-ext:config {
      deviate add {
      }
    }

    deviation /oc-netinst:network-instances/oc-netinst:network-instance/oc-netinst-ext:global-sag/oc-netinst-ext:config/oc-netinst-ext:anycast-mac {
      deviate add {
        sonic-ext:field-name "gwmac";
      }
    }

    deviation /oc-netinst:network-instances/oc-netinst:network-instance/oc-netinst-ext:global-sag/oc-netinst-ext:config/oc-netinst-ext:ipv4-enable {
      deviate add {
        sonic-ext:field-transformer "sag_ipv4_enable_xfmr";
      }
    }

    deviation /oc-netinst:network-instances/oc-netinst:network-instance/oc-netinst-ext:global-sag/oc-netinst-ext:config/oc-netinst-ext:ipv6-enable {
      deviate add {
        sonic-ext:field-transformer "sag_ipv6_enable_xfmr";
      }
    }
	
    deviation /oc-netinst:network-instances/oc-netinst:network-instance/oc-netinst-ext:global-sag/oc-netinst-ext:state {
      deviate add {
      }
    }

    deviation /oc-netinst:network-instances/oc-netinst:network-instance/oc-netinst-ext:global-sag/oc-netinst-ext:state/oc-netinst-ext:anycast-mac {
      deviate add {
      }
    }

    deviation /oc-netinst:network-instances/oc-netinst:network-instance/oc-netinst-ext:global-sag/oc-netinst-ext:state/oc-netinst-ext:ipv4-enable {
      deviate add {
      }
    }

    deviation /oc-netinst:network-instances/oc-netinst:network-instance/oc-netinst-ext:global-sag/oc-netinst-ext:state/oc-netinst-ext:ipv6-enable {
      deviate add {
      }
    }	

    deviation /oc-netinst:network-instances/oc-netinst:network-instance/oc-vxlan:neighbour-suppress {
        deviate add {
            sonic-ext:table-name "SUPPRESS_VLAN_NEIGH";
            sonic-ext:key-transformer "vlan_nd_suppress_key_xfmr";
        }
    }

    deviation /oc-netinst:network-instances/oc-netinst:network-instance/oc-vxlan:neighbour-suppress/oc-vxlan:config/oc-vxlan:arp-and-nd-suppress {
        deviate add {
            sonic-ext:field-transformer "vlan_nd_suppress_fld_xfmr";
        }
    }

    deviation /oc-netinst:network-instances/oc-netinst:network-instance/oc-vxlan:neighbour-suppress/oc-vxlan:state/oc-vxlan:arp-and-nd-suppress {
        deviate add {
            sonic-ext:field-transformer "vlan_nd_suppress_fld_xfmr";
        }
    }
    
    deviation /oc-netinst:network-instances/oc-netinst:network-instance/oc-vxlan:vxlan-vni-instances {
        deviate add {
            sonic-ext:subtree-transformer "vxlan_vni_instance_subtree_xfmr";
        }
    }    
}
