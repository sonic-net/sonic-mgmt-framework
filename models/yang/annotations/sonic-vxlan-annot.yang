module sonic-vxlan-annot {

    yang-version "1.1";

    namespace "http://github.com/Azure/sonic-vxlan-annot";
    prefix "svxlan-annot"; 

    import sonic-extensions { prefix sonic-ext; }
    import sonic-vxlan { prefix svxlan; }

    // meta
    organization
        "SONiC";

    contact
        "SONiC";

    description
        "SONIC vxlan";

    revision 2019-11-22 {
        description
            "Initial revision.";
    }

    deviation /svxlan:sonic-vxlan/svxlan:VXLAN_TUNNEL_TABLE/svxlan:VXLAN_TUNNEL_TABLE_LIST  {
        deviate add {
            sonic-ext:db-name "STATE_DB";
        }
    }

    deviation /svxlan:sonic-vxlan/svxlan:EVPN_REMOTE_VNI_TABLE/svxlan:EVPN_REMOTE_VNI_TABLE_LIST  {
        deviate add {
            sonic-ext:db-name "APPL_DB";
        }
    }

    deviation /svxlan:sonic-vxlan/svxlan:VXLAN_FDB_TABLE/svxlan:VXLAN_FDB_TABLE_LIST  {
        deviate add {
            sonic-ext:db-name "APPL_DB";
        }
    }
}
