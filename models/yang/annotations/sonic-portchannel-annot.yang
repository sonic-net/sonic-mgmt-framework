module sonic-portchannel-annot {

    yang-version "1";

    namespace "http://openconfig.net/yang/annotation/spc-annot";
    prefix "spc-annot";

    import sonic-portchannel { prefix spc; }
    import sonic-extensions { prefix sonic-ext; }


    deviation /spc:sonic-portchannel/spc:LAG_TABLE {
        deviate add {
            sonic-ext:db-name "APPL_DB";          
        }
    }

    deviation /spc:sonic-portchannel/spc:LAG_MEMBER_TABLE {
        deviate add {
            sonic-ext:db-name "APPL_DB";
        }
    }
}
