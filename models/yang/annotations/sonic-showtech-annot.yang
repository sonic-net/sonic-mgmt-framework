module sonic-showtech-annot {

    yang-version "1";

    namespace "http://openconfig.net/Azure/sonic-showtech-annot";
    prefix "showtech-annot";

    import sonic-extensions { prefix sonic-ext; }
    import sonic-show-techsupport { prefix sshwtchspt; }

    deviation /sshwtchspt:sonic-show-techsupport-info {
      deviate add {
        sonic-ext:rpc-callback "rpc_showtech_cb";
      }
    }

}
