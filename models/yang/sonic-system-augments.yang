module sonic-system-augments {

    yang-version "1";

    namespace "http://openconfig.net/yang/system";

    prefix "sys-agmnt";

    import openconfig-system { prefix oc-sys; }

    // meta
    organization "OpenConfig working group";

    contact
        "OpenConfig working group
        netopenconfig@googlegroups.com";

    description
        "Model for managing TACACS+ configurations .";

    revision 2019-11-05 {
        description
            "Initial augment file.";
    }

    // augment statements

    augment "/oc-sys:system/oc-sys:aaa/oc-sys:authentication/oc-sys:config" {
        leaf failthrough {
            type boolean;
            description "Indicating whether authentication failthrough should be enabled/disabled";
        }
    }

    augment "/oc-sys:system/oc-sys:aaa/oc-sys:server-groups/os-sys:server-group/oc-sys:servers/oc-sys:server/oc-sys:tacacs/oc-sys:config" {
        leaf  auth-type {
            type string;
            description "The server authentication type pap/chap/mschap";
        }
    }
}
