module openconfig-acl-annot {
  
    yang-version "1";

    namespace "http://openconfig.net/yang/annotation";
    prefix "oc-acl-annot";

    import sonic-extensions { prefix sonic-ext; }
    import openconfig-acl { prefix oc-acl; }

    deviation /oc-acl:acl/oc-acl:acl-sets/oc-acl:acl-set {
      deviate add {
        sonic-ext:table-name "ACL_TABLE";
        sonic-ext:key-delimiter "_";
      }
    }

    deviation /oc-acl:acl/oc-acl:acl-sets/oc-acl:acl-set/oc-acl:config/oc-acl:description {
      deviate add {
        sonic-ext:field-name "policy_desc";
      }
    }

    deviation /oc-acl:acl/oc-acl:acl-sets/oc-acl:acl-set/oc-acl:acl-entries/oc-acl:acl-entry {
      deviate add {
        sonic-ext:table-name "ACL_RULE";
        sonic-ext:key-transformer "acl_entry_key_xfmr";
      }
    }

    deviation /oc-acl:acl/oc-acl:acl-sets/oc-acl:acl-set/oc-acl:acl-entries/oc-acl:acl-entry/oc-acl:ipv4/oc-acl:config/oc-acl:source-address {
      deviate add {
        sonic-ext:field-name "SRC_IP";
      }
    }

    deviation /oc-acl:acl/oc-acl:acl-sets/oc-acl:acl-set/oc-acl:acl-entries/oc-acl:acl-entry/oc-acl:ipv4/oc-acl:config/oc-acl:destination-address {
      deviate add {
        sonic-ext:field-name "DST_IP";
      }
    }

    deviation /oc-acl:acl/oc-acl:acl-sets/oc-acl:acl-set/oc-acl:acl-entries/oc-acl:acl-entry/oc-acl:ipv4/oc-acl:config/oc-acl:protocol {
      deviate add {
        sonic-ext:field-transformer "acl_ip_protocol_xfmr";
      }
    } 

    deviation /oc-acl:acl/oc-acl:acl-sets/oc-acl:acl-set/oc-acl:acl-entries/oc-acl:acl-entry/oc-acl:ipv6/oc-acl:config/oc-acl:source-address {
      deviate add {
        sonic-ext:field-name "SRC_IP";
      }
    }

    deviation /oc-acl:acl/oc-acl:acl-sets/oc-acl:acl-set/oc-acl:acl-entries/oc-acl:acl-entry/oc-acl:ipv6/oc-acl:config/oc-acl:destination-address {
      deviate add {
        sonic-ext:field-name "DST_IP";
      }
    }

    deviation /oc-acl:acl/oc-acl:acl-sets/oc-acl:acl-set/oc-acl:acl-entries/oc-acl:acl-entry/oc-acl:ipv6/oc-acl:config/oc-acl:protocol {
      deviate add {
        sonic-ext:field-transformer "acl_ip_protocol_xfmr";
      }
    }

    deviation /oc-acl:acl/oc-acl:acl-sets/oc-acl:acl-set/oc-acl:acl-entries/oc-acl:acl-entry/oc-acl:transport/oc-acl:config/oc-acl:source-port {
      deviate add {
        sonic-ext:field-transformer "acl_source_port_xfmr";
      }
    }

    deviation /oc-acl:acl/oc-acl:acl-sets/oc-acl:acl-set/oc-acl:acl-entries/oc-acl:acl-entry/oc-acl:transport/oc-acl:config/oc-acl:destination-port {
      deviate add {
        sonic-ext:field-transformer "acl_destination_port_xfmr";
      }
    }

    deviation /oc-acl:acl/oc-acl:acl-sets/oc-acl:acl-set/oc-acl:acl-entries/oc-acl:acl-entry/oc-acl:transport/oc-acl:config/oc-acl:tcp_flags {
      deviate add {
        sonic-ext:field-transformer "acl_tcp_flags_xfmr";
      }
    }

    deviation /oc-acl:acl/oc-acl:acl-sets/oc-acl:acl-set/oc-acl:acl-entries/oc-acl:acl-entry/oc-acl:actions/oc-acl:config/oc-acl:forwrding-action {
      deviate add {
        sonic-ext:field-name "PACKET_ACTION";
      }
    }

    deviation /oc-acl:acl/oc-acl:interfaces {
      deviate add {
        sonic-ext:subtree-trasnformer "acl_port_bindings_xfmr";
      }
    }

}
