module sonic-mgmt-interface {
    namespace "http://github.com/Azure/sonic-mgmt-interface";
    prefix smgmtint;

    import ietf-yang-types {
        prefix yang;
    }

    import ietf-inet-types {
        prefix inet;
    }
    import sonic-mgmt-vrf {
        prefix mvrf;
    }

    import sonic-mgmt-port {
        prefix mgmtprt;
    }

    organization
        "SONiC";

    contact
        "SONiC";

    description
        "SONiC MANAGEMENT INTERFACE";

    revision 2019-11-13 {
        description
            "Initial revision.";
    }

    container sonic-mgmt-interface {

        container MGMT_INTERFACE {

            list MGMT_INTERFACE_LIST {

                key "portname";

                leaf portname{
                    type leafref {
                        path "/mgmtprt:sonic-mgmt-port/mgmtprt:MGMT_PORT/mgmtprt:MGMT_PORT_LIST/mgmtprt:ifname";
                    }
                }

                leaf vrf-name {
                    type leafref {
                        path "/mvrf:sonic-mgmt-vrf/mvrf:MGMT_VRF_CONFIG/mvrf:MGMT_VRF_CONFIG_LIST/mvrf:vrf_global_name";
                    }
                }
            }

            list MGMT_INTERFACE_IPADDR_LIST {

                key "portname ip_prefix";

                leaf portname{
                    type leafref {
                        path "/mgmtprt:sonic-mgmt-port/mgmtprt:MGMT_PORT/mgmtprt:MGMT_PORT_LIST/mgmtprt:ifname";
                    }
                }

                leaf ip_prefix {
                    type inet:ip-prefix;
                }

                leaf gwaddr {
                    type inet:ip-address;
                }

            }

        }

        container MGMT_INTF_TABLE {
            config false;

            list MGMT_INTF_TABLE_LIST {
                key "ifName";

                leaf ifName {
                    type string;
                }
            }

            list MGMT_INTF_TABLE_IPADDR_LIST {
                key "ifName ipPrefix";

                leaf ifName {
                   type string;
                }

                leaf ipPrefix {
                    type inet:ip-prefix;
                }
             }
        }

    }

}
