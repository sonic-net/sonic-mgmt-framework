module sonic-nat {
    namespace "http://github.com/Azure/sonic-nat";
    prefix snat;

    import ietf-yang-types {
        prefix yang;
    }

    import ietf-inet-types {
        prefix inet;
    }

    import sonic-common {
        prefix scommon;
    }

    import sonic-acl {
        prefix sacl;
    }

    organization
        "SONiC";

    contact
        "SONiC";

    description
        "SONiC NAT";

    revision 2020-01-22 {
        description
            "Adding RPC for clear NAT.";
    }

    revision 2019-10-30 {
        description
            "Initial revision.";
    }

    typedef nat-clear-param {
        type enumeration {
            enum ENTRIES {
                description "NAT dynamic Entries";
            }
            enum STATISTICS {
                description "NAT Statistics";
            }
        }
    }

    typedef nat-type {
        type enumeration {
            enum snat {
                description "Source NAT.";
            }
            enum dnat {
                description "Destination NAT.";
            }
        }
    }

    typedef ip-protocol-type {
        type enumeration {
            enum TCP;
            enum UDP;
        }
    }

    grouping sonic-twice-nat-id {

        leaf twice_nat_id {
            type uint16 {
                range "1..9999" {
                    error-message "Invalid Group Id for twice NAPT.";
                    error-app-tag twice-nat-id-invalid;
                }
            }
        }
    }

    grouping sonic-nat-common {

        leaf global_ip {
            type inet:ipv4-address;
        }

        leaf local_ip {
            mandatory true;
            type inet:ipv4-address;
        }

        leaf nat_type {
            type nat-type;
            default dnat;
        }
        uses sonic-twice-nat-id;
    }

    typedef ip-address {
        type union {
          type inet:ipv4-address;
          type string {
                          pattern '(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9])(-(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9])\.(25[0-5]|2[0-4][0-9]|1[0-9][0-9]|[1-9]?[0-9]))?';
                      }
        }

        description
          "This type denotes a single IP address or a range of addresses.";
    }

    container sonic-nat {

        container STATIC_NAPT {

            list STATIC_NAPT_LIST {
                key "global_ip ip_protocol global_l4_port";


                leaf ip_protocol {
                    type ip-protocol-type;
                }

                leaf global_l4_port {
                    type inet:port-number ;
                }

                leaf local_port {
                    mandatory true;
                    type inet:port-number ;
                }

                uses sonic-nat-common;

            }
        }

        container STATIC_NAT {
            list STATIC_NAT_LIST {
                key "global_ip";

                uses sonic-nat-common;
            }
        }

        typedef mode {
            type enumeration {
                enum enabled;
                enum disabled;
            }
        }

        container NAT_GLOBAL {
            list NAT_GLOBAL_LIST {
                key "name";
                max-elements 1;

                leaf name {
                    type enumeration {
                        enum Values;
                    }
                }
                leaf admin_mode {
                    type mode;
                    default enabled;
                }

                leaf nat_timeout {
                    type uint32 {
                        range "300..432000" {
                            error-message "Invalid NAT Timeout, valid range 300 sec to 432000 sec.";
                            error-app-tag nat-timeout-invalid;
                        }
                    }
                }
                leaf nat_tcp_timeout {
                    type uint32 {
                        range "300..432000" {
                            error-message "Invalid NAT TCP Timeout, valid range 300 sec to 432000 sec.";
                            error-app-tag nat-tcp-timeout-invalid;
                        }
                    }
                }
                leaf nat_udp_timeout {
                    type uint16 {
                        range "120..600" {
                            error-message "Invalid NAT UDP Timeout, valid range 120 sec to 600 sec.";
                            error-app-tag nat-udp-timeout-invalid;
                        }
                    }
                }
            }
        }

        container NAT_POOL {
            list NAT_POOL_LIST {
                key "pool_name";
                max-elements 16;

                leaf pool_name {
                    type string {
                        pattern '[a-zA-Z0-9]{1}([-a-zA-Z0-9_]{0,31})';
                        length 1..32 {
                            error-app-tag pool-name-invalid-length;
                        }
                    }
                }

                leaf nat_ip {
                    type ip-address;
                }

                leaf nat_port {
                    type string {
                        pattern "[0-9]{1,5}(-)[0-9]{1,5}";
                    }
                }
            }
        }

        container NAT_BINDINGS {

            list NAT_BINDINGS_LIST {

                key "name";
                max-elements 16;

                leaf name {
                    type string {

                        pattern '[a-zA-Z0-9]{1}([-a-zA-Z0-9_]{0,31})';
                        length 1..32 {
                            error-app-tag binding-name-invalid-length;
                        }
                    }
                }

                leaf nat_pool {
                    mandatory true;
                    type leafref {
                        path "../../../NAT_POOL/NAT_POOL_LIST/pool_name";
                    }
                }

                leaf access_list {
                    type leafref {
                        path "/sacl:sonic-acl/sacl:ACL_TABLE/sacl:ACL_TABLE_LIST/sacl:aclname";
                    } 
                }

                leaf nat_type {
                    type nat-type;
                    default snat;
                }
                uses sonic-twice-nat-id;
            }
        }
    }

    rpc clear_nat {
        input {
            leaf nat-param {
                type nat-clear-param;
                description
                    "Parameter for deleting either all dynamic NAT entries or all NAT statistics";
            }
        }
        output {
            leaf status {
                type string;
                description
                    " Success / Failure of deletion of NAT Parameters";
            }
        }
    }
}
