module sonic-spanning-tree {
    namespace "http://github.com/Azure/sonic-spanning-tree";
    prefix sstp;
    yang-version 1.1;

    import sonic-port {
        prefix prt;
    }

    import sonic-portchannel {
        prefix spc;
    }

    import sonic-vlan {
        prefix svlan;
    }

    organization
        "BRCM";

    contact
        "BRCM";

    description
        "SONIC Spanning-tree";

    revision 2019-09-21 {
        description
            "Initial revision.";
    }

    grouping vlanModeAttr {
        leaf forward_delay {
            type uint8 {
                range "4..30" {
                    error-message "Invalid Forwarding Delay value.";
                }
            }
            units seconds;
            default 15;
            description
                "The delay used by STP bridges to transition root and
                designated ports to forwarding";
        }

        leaf hello_time {
            type uint8 {
                range "1..10" {
                    error-message "Invalid Hello Time value.";
                }
            }
            units seconds;
            default 2;
            description
                "The interval between periodic transmissions of
                configuration messages by designated ports";
        }

        leaf max_age {
            type uint8 {
                range "6..40" {
                    error-message "Invalid Maximum Age Time value.";
                }
            }
            units seconds;
            default 20;
            description
                "The maximum age of the information transmitted by the
                bridge when it is the root bridge";
        }

        leaf priority {
            type uint16 {
                range "0..61440" {
                    error-message "Invalid Bridge Priority value.";
                }
            }
            default 32768;
            description
                "The manageable component of the Bridge Identifier";
        }
    }

    grouping interfaceAttr {
        leaf path_cost {
            type uint64 {
                range "1..200000000" {
                    error-message "Invalid Port Path Cost value.";
                }
            }
            default 200;
            description
                "The port's contribution, when it is the Root Port,
                to the Root Path Cost for the Bridge";
        }

        leaf priority {
            type uint8 {
                range "0..240" {
                    error-message "Invalid Port Priority value.";
                }
            }
            default 128;
            description
                "The manageable component of the Port Identifier,
                also known as the Port Priority";
        }
    }

    container sonic-spanning-tree {

        container STP {
            list STP_LIST {
                max-elements 1;
                key "keyleaf";

                leaf keyleaf {
                    type enumeration {
                        enum GLOBAL;
                    }
                    description
                        "Key node identifier. It's value is always GLOBAL";
                }

                leaf mode {
                    type enumeration {
                        enum pvst;
                        enum rpvst;
                        enum mstp;
                        enum rstp;
                    }
                    description
                        "Spanning tree mode";
                }

                leaf rootguard_timeout {
                    type uint16 {
                        range "5..600" {
                            error-message "Invalid Root-guard Timeout value.";
                        }
                    }
                    units seconds;
                    default 30;
                    description
                        "Once superior BPDUs stop coming on the port, device
                        will wait for a period until root guard timeout before
                        moving the port to forwarding state";
                }

                leaf bpdu_filter {
                    type boolean;
                    description
                        "Enable edge port BPDU filter";
                }

                uses vlanModeAttr;
            }
        }

        container STP_VLAN {
            list STP_VLAN_LIST {
                key "name";

                leaf name {
                    type leafref {
                        path "/svlan:sonic-vlan/svlan:VLAN/svlan:VLAN_LIST/svlan:name";
                    }
                    description
                        "Vlan identifier";
                }

                leaf vlanid {
                    type uint16 {
                        range "1..4095" {
                            error-message "Vlan ID out of range";
                            error-app-tag vlanid-invalid;
                        }
                    }
                    description
                        "Vlan identifier number";
                }

                leaf enabled {
                    type boolean;
                    description
                        "Spanning tree enabled/disabled on Vlan";
                }

                uses vlanModeAttr;
            }
        }

        container STP_VLAN_PORT {
            list STP_VLAN_PORT_LIST {
                key "vlan-name ifname";

                leaf vlan-name {
                    type leafref {
                        path "../../../STP_VLAN/STP_VLAN_LIST/name";
                    }
                    description
                        "Reference to Vlan";
                }

                leaf ifname {
                    type leafref {
                        path "../../../STP_PORT/STP_PORT_LIST/ifname";
                    }
                    description
                        "Reference to Ethernet interface or PortChannel";
                }

                uses interfaceAttr;
            }
        }

        container STP_PORT {
            list STP_PORT_LIST {
                key "ifname";

                leaf ifname {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                    }
                    description
                        "Reference to Ethernet interface or PortChannel";
                }

                leaf enabled {
                    type boolean;
                    description
                        "Spanning tree enabled/disabled on Interface";
                }

                leaf root_guard {
                    type boolean;
                    description
                        "Enable/Disable Root guard on port";
                }

                leaf bpdu_guard {
                    type boolean;
                    description
                        "Enable/Disable port BPDU guard";
                }

                leaf bpdu_filter {
                    type enumeration {
                        enum enable;
                        enum disable;
                        enum global;
                    }
                    description
                        "Enable port BPDU filter. Permissible values are 
                        'enable', 'disable' and 'global'";
                }

                leaf bpdu_guard_do_disable {
                    type boolean;
                    description
                        "Port to be disabled when it receives a BPDU";
                }

                leaf uplink_fast {
                    type boolean;
                    description
                        "Enable/Disable uplink-fast on port";
                }

                leaf portfast {
                    type boolean;
                    description
                        "Enable/Disable portfast on port";
                }

                uses interfaceAttr;

                // For RPVST+
                leaf edge_port {
                    must "../../../STP/STP_LIST[keyleaf='GLOBAL']/mode='rpvst'" {
                        error-message "Configuration allowed in Rapid PVST mode";
                        error-app-tag stp-invalid;
                    }
                    type boolean;
                    description
                        "Enable/Disable Edge-port on interface";
                }

                leaf link_type {
                    must "../../../STP/STP_LIST[keyleaf='GLOBAL']/mode='rpvst'" {
                        error-message "Configuration allowed in Rapid PVST mode";
                        error-app-tag stp-invalid;
                    }
                    type enumeration {
                        enum auto;
                        enum shared;
                        enum point-to-point;
                    }
                    description
                        "Specifies the interface's link type. Permissible values
                        are 'shared', 'point-to-point' and 'auto'";
                }
            }
        }
    }
}
