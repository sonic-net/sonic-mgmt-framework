module sonic-udld {
    namespace "http://github.com/Azure/sonic-udld";
    prefix sudld;
    yang-version 1.1;

    import sonic-extension {
        prefix sonic-ext;
    }

    import sonic-port {
        prefix prt;
    }

    organization
        "SONiC";

    contact
        "SONiC";

    description
        "SONiC UDLD yang model";

    revision 2019-11-08 {
        description
            "Initial revision.";
    }

    grouping udld_mode_config {
        leaf admin_enable {
            type boolean;
            description
                "Enable/Disable UDLD";
        }

        leaf aggressive {
            type boolean;
            description
                "Enable/Disable aggressive mode of UDLD";
        }
    }

    container sonic-udld {

        container UDLD {
            list UDLD_LIST {
                key "id";

                leaf id {
                    type enumeration {
                        enum GLOBAL;
                    }
                    description
                        "It's value is always GLOBAL";
                }

                uses udld_mode_config;

                leaf msg_time {
                    type uint8 {
                        range "1..30" {
                            error-message "Invalid UDLD message time value.";
                        }
                    }
                    units seconds;
                    default 1;
                    description
                        "It is the time interval at which periodic hellos are
                        exchanged. Default is 1 second";
                }

                leaf multiplier {
                    type uint8 {
                        range "3..10" {
                            error-message "Invalid UDLD multiplier value.";
                        }
                    }
                    default 3;
                    description
                        "This multiplier value is used to determine the timeout
                        interval (i.e. message-time x multiplier value) after
                        which UDLD declares the state of the link.";
                }
            }
        }

        container UDLD_PORT {
            list UDLD_PORT_LIST {
                key "ifname";

                must "count(../../UDLD/UDLD_LIST[id='GLOBAL']) != 0" {
                    error-message "UDLD not enabled globally";
                    error-app-tag udld-invalid;
                }

                leaf ifname {
                    type leafref {
                        path "/prt:sonic-port/prt:PORT/prt:PORT_LIST/prt:ifname";
                    }
                    description
                        "Reference of port on which UDLD to be configured.";
                }

                uses udld_mode_config;
            }
        }

        container _UDLD_GLOBAL_TABLE {
            config false;

            list _UDLD_GLOBAL_TABLE_LIST {
                sonic-ext:db-name "APPL_DB";
                key "id";

                leaf id {
                    type enumeration {
                        enum GLOBAL;
                    }
                    description
                        "It's value is always GLOBAL";
                }

                leaf device_id {
                    type string;
                    description
                        "Local device Id";
                }

                leaf device_name {
                    type string;
                    description
                        "Name of local device";
                }

                leaf timeout_interval {
                    type uint16;
                    description
                        "Timeout interval (message time x multipler)";
                }
            }
        }

        container _UDLD_PORT_TABLE {
            config false;

            list _UDLD_PORT_TABLE_LIST {
                sonic-ext:db-name "APPL_DB";
                key "ifname";

                leaf ifname {
                    type leafref {
                        path "/prt:sonic-port/prt:PORT/prt:PORT_LIST/prt:ifname";
                    }
                    description
                        "Reference of port on which UDLD is configured.";
                }

                leaf status {
                    type string;
                    description
                        "UDLD status on port";
                }

                leaf pdu_sent {
                    type uint64;
                    description
                        "Count of PDUs transmitted from port";
                }

                leaf pdu_received {
                    type uint64;
                    description
                        "Count of PDUs received on port";
                }

                leaf pdu_recv_error {
                    type uint64;
                    description
                        "Count of PDUs errors received on port";
                }
            }
        }

        container _UDLD_PORT_NEIGH_TABLE {
            config false;

            list _UDLD_PORT_NEIGH_TABLE_LIST {
                sonic-ext:db-name "APPL_DB";
                key "ifname index";

                leaf ifname {
                    type leafref {
                        path "/prt:sonic-port/prt:PORT/prt:PORT_LIST/prt:ifname";
                    }
                    description
                        "Reference of local port on which UDLD is configured.";
                }

                leaf index {
                    type string;
                    description
                        "Index number of neighbor port";
                }

                leaf device_id {
                    type string;
                    description
                        "Peer device id";
                }

                leaf device_name {
                    type string;
                    description
                        "Peer device name";
                }

                leaf port_id {
                    type string;
                    description
                        "Peer port name";
                }

                leaf msg_time {
                    type uint16;
                    description
                        "Message time of peer";
                }

                leaf timeout_interval {
                    type uint16;
                    description
                        "Timeout interval of peer";
                }

                leaf status {
                    type string;
                    description
                        "Peer Port status";
                }
            }
        }
    }
}
