module sonic-bgp-peergroup-af {
  namespace "http://github.com/Azure/sonic-bgp-peergroup-af";
  prefix pgaf;

  import ietf-yang-types {
    prefix yang;
  }

  import ietf-inet-types {
    prefix inet;
  }

  import sonic-common {
    prefix scommon;
  }
  
  import sonic-bgp-peergroup {
    prefix pg;
  }

  organization
    "SONiC";

  contact
    "SONiC";

  description
    "SONIC BGP Peer Group AF YANG";

  revision 2019-10-27 {
    description
      "Initial revision.";
  }

  container sonic-bgp-peergroup-af {
    container BGP_PEER_GROUP_AF {
      list BGP_PEER_GROUP_AF_LIST {
        key "vrf_name peer_group_name afi_safi";

        leaf vrf_name {
            type string;
        }

        leaf peer_group_name {
            type string;
        }

        leaf afi_safi {
          type string;
        }

        leaf admin {
          type boolean;
        }
       
        leaf send_default_route {
          type boolean;
        }

        leaf max_prefix_limit {
          type uint32;
        }

        leaf max_prefix_warning_only {
          type boolean;
        }

        leaf max_prefix_warning_threshold {
          type uint8 {
            range "0..100";
          }
        }

        leaf max_prefix_restart_interval {
          type uint16 {
            range "1..3600";
          }
        }

        leaf-list route_map_in {
          type string;
        }

        leaf-list route_map_out {
          type string;
        }
      }
    }
  }
}
