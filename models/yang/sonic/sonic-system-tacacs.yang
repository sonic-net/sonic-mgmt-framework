module sonic-system-tacacs {
    namespace "http://github.com/Azure/sonic-system-tacacs";
    prefix ssys;

    import ietf-inet-types {
        prefix inet;
    }

    revision 2019-11-13 {
        description "Initial revision.";
    }

    typedef auth_type_enumeration {
        type enumeration {
            enum pap;
            enum chap;
            enum mschap;
        }
    }

    container sonic-system-tacacs {

        container TACPLUS_SERVER {
            list TACPLUS_SERVER_LIST {
                max-elements 8;
                key "ipaddress";

                leaf ipaddress {
                    type inet:ip-address;
                }

                leaf priority {
                    default 1;
                    type uint8 {
                        range "1..64" {
                            error-message "TACACS server priority must be 1..64";
                        }
                    }
                }

                leaf tcp_port {
                    type inet:port-number;
                    default 49;
                }

                leaf timeout {
                    default 5;
                    type uint16 {
                        range "1..60" {
                            error-message "TACACS server timeout must be 1..60";
                        }
                    }
                }

                leaf auth_type {
                    type auth_type_enumeration;
                    default pap;
                }

                leaf passkey {
                    type string {
                        length "1..32";
                        pattern "[0-9A-Za-z]*" {
                            error-message "TACACS shared secret valid chars: [0-9A-Za-z]";
                        }
                    }
                }
            }
        }


        container TACPLUS {
            list TACPLUS_LIST {

                key "type";

                leaf type {
                    type enumeration {
                        enum global;
                    }
                }

                leaf auth_type {
                    type auth_type_enumeration;
                    default pap;
                }

                leaf timeout {
                    type uint16 {
                        range "1..60" {
                            error-message "TACACS timeout must be 1..60";
                        }
                    }
                    default 5;
                }

                leaf passkey {
                    type string {
                        length "1..32";
                        pattern "[0-9A-Za-z]*" {
                            error-message "TACACS shared secret valid chars: [0-9A-Za-z]";
                        }
                    }
                }

                leaf src_ip {
                    type inet:ip-address;
                }

            }
        }
    }
}
