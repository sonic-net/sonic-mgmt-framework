module sonic-config-mgmt {
  namespace "http://github.com/Azure/sonic-config-mgmt";
  prefix scm;


  organization
    "SONiC";
  contact
    "SONiC";
  description
    "SONIC Configuration Management";

  revision 2019-09-15 {
    description
      "Initial revision.";
  }


  typedef filename-uri-type {
    description
      "Support for following URI format:
         file://etc/sonic/filename
         Exception: running-configuration (running configDB)
                    startup-configuration (default startup config file i.e. file://etc/sonic/config_db.json)";
       type string {
            pattern "((file):.*)";
            pattern "running-configuration";
            pattern "startup-configuration";
       }
  }

  rpc copy {
      input {
          leaf source {
              type filename-uri-type;
              description "Provide the filename in URI format for the source file.";
          }

          leaf overwrite {
              type boolean;
              description "Overwrite the destination.";  
          }

          leaf destination {
              type filename-uri-type;
              description "Provide the filename in URI format for the destination file.";
          }
      }

      output {
        leaf status {
            type int32;
            description "The status of the operation execution request.";
        }
        leaf status-detail {
            type string;
            description "The detailed status of the operation execution request.";
      }
    }
  }

  rpc write-erase {
      description
          "Configuration Erase Features:
             - op_write_erase : Erase configuration files except for the management interface configuration.
             - op_write_erase_boot : Erase the configuration files including the management interface configuration.
             - op_write_erase_install : Restore SONiC switch content to default values.
             - op_no_write_erase : Cancel configuration erase operation.

           The detailed result of the requested command is sent as a string.";
      input {
          leaf subcmd {
              type string;
              description "Subcommand: op_write_erase | op_write_erase_boot | op_write_erase_install | op_no_write_erase";
          }
      }

      output {
        leaf status {
            type int32;
            description "The status of the operation execution request.";
        }
        leaf status-detail {
            type string;
            description "The detailed status of the operation execution request.";
      }
    }
  }

}
