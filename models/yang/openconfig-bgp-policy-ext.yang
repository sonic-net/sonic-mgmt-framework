module openconfig-bgp-policy-ext {

  yang-version "1";

  // namespace
  namespace "http://openconfig.net/yang/bgp-policy/extension";

  prefix "oc-bgp-pol-ext";

  import openconfig-routing-policy {prefix oc-rpol; }
  import openconfig-bgp-types { prefix oc-bgp-types; }
  import openconfig-bgp-policy { prefix oc-bgp-pol; }

  description
    "This module describes a deviation for BGP routing policy 
     configuration extensions.";

  revision "2019-11-13" {
    description
      "BGP Routing Policy extensions.";
  }

  grouping routing-policy-ext-action-next-hop-set {
      leaf next-hop-set {
          type leafref {
              path "/oc-rpol:routing-policy/oc-rpol:defined-sets/oc-rpol:prefix-sets/oc-rpol:prefix-set/oc-rpol:config/oc-rpol:name";
          }
          description "References a defined prefix set";
      }
  }

  typedef bgp-community-defined-regexp-type {
      // Format REGEX:string 
      type string;
     // {
          // regex 
        //  pattern '^(REGEX:[0-9a-zA-Z]{1,10})$';
     // }

      description
          "Type definition for communities specified as regular
          expression patterns";
    }

  deviation /oc-rpol:routing-policy/oc-rpol:defined-sets/oc-bgp-pol:bgp-defined-sets/oc-bgp-pol:community-sets/oc-bgp-pol:community-set/oc-bgp-pol:config/oc-bgp-pol:community-member {
      deviate replace {
          type union {
              type oc-bgp-types:bgp-std-community-type;
              type bgp-community-defined-regexp-type;
              type oc-bgp-types:bgp-well-known-community-type;
          }
      }
  }

  deviation /oc-rpol:routing-policy/oc-rpol:defined-sets/oc-bgp-pol:bgp-defined-sets/oc-bgp-pol:ext-community-sets/oc-bgp-pol:ext-community-set/oc-bgp-pol:config/oc-bgp-pol:ext-community-member {
      deviate replace {
          type union {
              type oc-bgp-types:bgp-ext-community-type;
              type bgp-community-defined-regexp-type;
          }
      }
  }

  augment /oc-rpol:routing-policy/oc-rpol:policy-definitions/oc-rpol:policy-definition/oc-rpol:statements/oc-rpol:statement/oc-rpol:conditions/oc-bgp-pol:bgp-conditions/oc-bgp-pol:config {
      uses routing-policy-ext-action-next-hop-set;
  }

  augment /oc-rpol:routing-policy/oc-rpol:policy-definitions/oc-rpol:policy-definition/oc-rpol:statements/oc-rpol:statement/oc-rpol:conditions/oc-bgp-pol:bgp-conditions/oc-bgp-pol:state {
      uses routing-policy-ext-action-next-hop-set;
  }

  // rpc statements

  // notification statements
}
