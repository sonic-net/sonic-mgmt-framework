module openconfig-interfaces-ext {

    yang-version "1";

    // namespace
    namespace "http://openconfig.net/yang/interfaces/extention";

    prefix "oc-intf-ext";

    import openconfig-interfaces { prefix oc-intf; }
    import openconfig-vlan { prefix oc-vlan; }
    import openconfig-if-ip {prefix oc-ip; }
    import openconfig-if-ip-ext {prefix oc-ip-ext; }
    import openconfig-if-ethernet {prefix oc-eth; }
    import openconfig-inet-types { prefix oc-inet; }
    import openconfig-lacp {prefix oc-lacp; }
    import openconfig-if-poe {prefix oc-poe; }
    import openconfig-if-tunnel {prefix oc-tun; }
    import openconfig-if-aggregate {prefix oc-lag; }
    import ietf-inet-types { prefix ietf-inet; }
    import openconfig-yang-types { prefix oc-yang; }

    augment "/oc-intf:interfaces/oc-intf:interface/oc-lag:aggregation/oc-lag:config" {
        leaf fallback {
            type boolean;
            description "Indicating whether lacp fallback is enabled or not";
        }
    }
    augment "/oc-intf:interfaces/oc-intf:interface/oc-lag:aggregation/oc-lag:state" {
        leaf fallback {
            type boolean;
            description "Fallback status on this interface";
        }
    }
    augment "/oc-lacp:lacp/oc-lacp:interfaces/oc-lacp:interface/oc-lacp:members/oc-lacp:member/oc-lacp:state" {
        leaf selected {
            type boolean;
            description "Selected status on this interface";
        }
    }

    augment "/oc-intf:interfaces/oc-intf:interface/oc-intf:subinterfaces/oc-intf:subinterface/oc-ip:ipv4/oc-ip:addresses/oc-ip:address/oc-ip:config" {
        leaf gw-addr {
            type oc-inet:ipv4-address;
            description "IPv4 Gateway address";
        }
    }
    augment "/oc-intf:interfaces/oc-intf:interface/oc-intf:subinterfaces/oc-intf:subinterface/oc-ip:ipv4/oc-ip:addresses/oc-ip:address/oc-ip:state" {
        leaf gw-addr {
            type oc-inet:ipv4-address;
            description "IPv4 Gateway address";
        }
    }
    augment "/oc-intf:interfaces/oc-intf:interface/oc-intf:subinterfaces/oc-intf:subinterface/oc-ip:ipv6/oc-ip:addresses/oc-ip:address/oc-ip:config" {
        leaf gw-addr {
            type oc-inet:ipv6-address;
            description "IPv6 Gateway address";
        }
    }
    augment "/oc-intf:interfaces/oc-intf:interface/oc-intf:subinterfaces/oc-intf:subinterface/oc-ip:ipv6/oc-ip:addresses/oc-ip:address/oc-ip:state" {
        leaf gw-addr {
            type oc-inet:ipv6-address;
            description "IPv6 Gateway address";
        }
    }

    augment "/oc-intf:interfaces/oc-intf:interface/oc-eth:ethernet/oc-eth:state/oc-eth:counters" {
        leaf out-oversize-frames {
            type oc-yang:counter64;
            description
                "The total number of frames transmitted that were
                longer than 1518 octets (excluding framing bits,
                but including FCS octets) and were otherwise
                well formed.";
        }
    }

    grouping interface-nat-zone-config {
        leaf nat-zone {
            description
                "NAT zone id.";
            type uint8 {
                range "0..3";
            }
        }
    }
    grouping interface-nat-zone-top {
        container nat-zone {
            container config {
                uses interface-nat-zone-config;
            }
            container state {
                config false;
                uses interface-nat-zone-config;
            }
        }
    }

	grouping interface-sag-ipv4-config {
        leaf-list static-anycast-gateway {
            description
                "Static Anycast Gateway addresses";
			max-elements 16;
			type ietf-inet:ipv4-prefix;
        }
    }
	
    grouping interface-sag-ipv4-top {
        container sag-ipv4 {
            container config {
                uses interface-sag-ipv4-config;
            }
            container state {
                config false;
                uses interface-sag-ipv4-config;
            }
        }
    }	

	grouping interface-sag-ipv6-config {
        leaf-list static-anycast-gateway {
            description
                "Static Anycast Gateway addresses";
			max-elements 16;
			type ietf-inet:ipv6-prefix;
        }
    }
	
    grouping interface-sag-ipv6-top {
        container sag-ipv6 {
            container config {
                uses interface-sag-ipv6-config;
            }
            container state {
                config false;
                uses interface-sag-ipv6-config;
            }
        }
    }
	
    augment "/oc-intf:interfaces/oc-intf:interface" {
        description
            "NAT zone config and state data.";
        uses interface-nat-zone-top;
    }
	
	augment "/oc-intf:interfaces/oc-intf:interface/oc-intf:subinterfaces/oc-intf:subinterface/oc-ip:ipv4" {
        description
            "SAG config and state data.";
        uses interface-sag-ipv4-top {
			when "oc-intf:config/oc-intf:type = 'oc-intf-types-ext:IF_NVE'";
			description
			  "SAG interface config/state";
		}		  
	}

	augment "/oc-intf:interfaces/oc-intf:interface/oc-intf:subinterfaces/oc-intf:subinterface/oc-ip:ipv6" {
        description
            "SAG config and state data.";
        uses interface-sag-ipv6-top {
			when "oc-intf:config/oc-intf:type = 'oc-intf-types-ext:IF_NVE'";
			description
			  "SAG interface config/state";
		}		  
	}
	
    deviation /oc-intf:interfaces/oc-intf:interface/oc-intf:hold-time {
        deviate not-supported;
    }

    deviation /oc-intf:interfaces/oc-intf:interface/oc-intf:subinterfaces/oc-intf:subinterface/oc-intf:state {
        deviate not-supported;
    }

    deviation /oc-intf:interfaces/oc-intf:interface/oc-intf:subinterfaces/oc-intf:subinterface/oc-vlan:vlan {
        deviate not-supported;
    }

    deviation /oc-intf:interfaces/oc-intf:interface/oc-intf:subinterfaces/oc-intf:subinterface/oc-ip:ipv4/oc-ip:addresses/oc-ip:address/oc-ip:vrrp {
        deviate not-supported;
    }
    deviation /oc-intf:interfaces/oc-intf:interface/oc-intf:subinterfaces/oc-intf:subinterface/oc-ip:ipv4/oc-ip:proxy-arp {
        deviate not-supported;
    }
    deviation /oc-intf:interfaces/oc-intf:interface/oc-intf:subinterfaces/oc-intf:subinterface/oc-ip:ipv4/oc-ip:config {
        deviate not-supported;
    }
    deviation /oc-intf:interfaces/oc-intf:interface/oc-intf:subinterfaces/oc-intf:subinterface/oc-ip:ipv4/oc-ip:state {
        deviate not-supported;
    }

    deviation /oc-intf:interfaces/oc-intf:interface/oc-intf:subinterfaces/oc-intf:subinterface/oc-ip:ipv6/oc-ip:addresses/oc-ip:address/oc-ip:vrrp {
        deviate not-supported;
    }
    deviation /oc-intf:interfaces/oc-intf:interface/oc-intf:subinterfaces/oc-intf:subinterface/oc-ip:ipv6/oc-ip:router-advertisement {
        deviate not-supported;
    }
    deviation /oc-intf:interfaces/oc-intf:interface/oc-intf:subinterfaces/oc-intf:subinterface/oc-ip:ipv6/oc-ip:unnumbered {
        deviate not-supported;
    }
    deviation /oc-intf:interfaces/oc-intf:interface/oc-intf:subinterfaces/oc-intf:subinterface/oc-ip:ipv6/oc-ip:config {
        deviate not-supported;
    }
    deviation /oc-intf:interfaces/oc-intf:interface/oc-intf:subinterfaces/oc-intf:subinterface/oc-ip:ipv6/oc-ip:state {
        deviate not-supported;
    }
    deviation /oc-intf:interfaces/oc-intf:interface/oc-intf:subinterfaces/oc-intf:subinterface/oc-ip:ipv6/oc-ip-ext:autoconf {
        deviate not-supported;
    }

    deviation /oc-intf:interfaces/oc-intf:interface/oc-eth:ethernet/oc-poe:poe {
        deviate not-supported;
    }
    deviation /oc-intf:interfaces/oc-intf:interface/oc-vlan:routed-vlan {
        deviate not-supported;
    }
    deviation /oc-intf:interfaces/oc-intf:interface/oc-tun:tunnel {
        deviate not-supported;
    }
}
