module sonic-acl-deviation {
	namespace "http://github.com/Azure/sonic-acl-deviation";
	prefix acld;
	yang-version 1.1;

	import sonic-acl {
		prefix sacl;
	}

	organization
		"SONiC";

	contact
		"SONiC";

	description
		"SONIC ACL Deviations";

	revision 2019-05-15 {
		description
			"Initial revision.";
	}
/*
	deviation /sacl:sonic-acl/sacl:ACL_TABLE/sacl:type {
		deviate replace {
			type enumeration {
				enum MIRROR;
				enum L2;
				enum L3;
			}
		}
	}

	deviation /sacl:sonic-acl/sacl:ACL_RULE/sacl:PACKET_ACTION {
		deviate replace {
			type enumeration {
				enum FORWARD;
				enum DROP;
			}
		}
	}
	*/
}
