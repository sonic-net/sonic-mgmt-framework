module sonic-portchannel {
	namespace "http://github.com/Azure/sonic-portchannel";
	prefix spc;

	import sonic-common {
		prefix scommon;
	}

	import sonic-port {
		prefix prt;
	}

	organization
		"SONiC";

	contact
		"SONiC";

	description
		"SONIC PORTCHANNEL";

	revision 2019-05-15 {
		description
			"Initial revision.";
	}

	container sonic-portchannel {

		container PORTCHANNEL {

			list PORTCHANNEL_LIST {
				key "name";

				max-elements 3;

				leaf name {
					type string;
				}

				leaf admin_status {
					type scommon:admin-status;
				}

				leaf mtu {
					type uint16;
				}

				leaf min_links {
					type uint8;
				}

				leaf fallback {
					type boolean;
				}
			}
		}

		container PORTCHANNEL_MEMBER { 

			list PORTCHANNEL_MEMBER_LIST { 
				key "name ifname";

				leaf name {
					type leafref {
						path "../../../PORTCHANNEL/PORTCHANNEL_LIST/name";
					}
				}

				leaf ifname {
					type leafref {
						path "/prt:sonic-port/prt:PORT/prt:PORT_LIST/prt:ifname";
					}
				}
			}
		}
	}
}
