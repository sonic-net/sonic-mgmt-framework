module sonic-buffer-pool {
	namespace "http://github.com/Azure/sonic-buffer-pool";
	prefix bpl;

	organization
		"SONiC";

	contact
		"SONiC";

	description
		"SONIC BUFFER POOL";

	revision 2019-05-15 {
		description
			"Initial revision.";
	}

	container sonic-buffer-pool {

		container BUFFER_POOL {

			list BUFFER_POOL_LIST {
				key "name";

				leaf name {
					type string;
				}

				leaf type {
					type enumeration {
						enum ingress;
						enum egress;
					}
				}

				leaf mode {
					type enumeration {
						enum static;
						enum dynamic;
					}
				}

				leaf size {
					type uint64;
				}

			}
		}
	}
}
