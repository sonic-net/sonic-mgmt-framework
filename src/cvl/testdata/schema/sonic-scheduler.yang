module sonic-scheduler {
	namespace "http://github.com/Azure/sonic-scheduler";
	prefix sch;

	organization
		"SONiC";

	contact
		"SONiC";

	description
		"SONIC SCHEDULER";

	revision 2019-05-15 {
		description
			"Initial revision.";
	}

	container sonic-scheduler {

		container SCHEDULER {

			list SCHEDULER_LIST {
				key "name";

				leaf name{
					type string;
				}

				leaf type {
					type enumeration {
						enum DWRR;
						enum WRR;
						enum PRIORITY;
					}
				}

				leaf weight {
					type uint8 {
						range "0..255";
					}
				}

				leaf priority {
					type uint8 {
						range "0..9";
					}
				}
			}
		}
	}
}
