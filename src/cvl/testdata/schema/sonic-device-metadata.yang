module sonic-device-metadata {
	yang-version 1.1;
	namespace "http://github.com/Azure/sonic-device-metadata";
	prefix sdm;

	import ietf-yang-types {
		prefix yang;
	}

	import sonic-common {
		prefix scommon;
	}

	import sonic-bgp-global {
		prefix sbg;
	}

	organization
		"SONiC";

	contact
		"SONiC";

	description
		"SONIC DEVICE METADATA";

	revision 2019-07-02 {
		description
			"Initial revision.";
	}

	container sonic-device-metadata {

		container DEVICE_METADATA {

			list DEVICE_METADATA_LIST {
				key "name";
				max-elements 1;

				leaf name{
					type string;
				}

				leaf vrf_name {
					type enumeration {
						enum default;
					}
					default default;
				}

				leaf hwsku {
					type string;
				}

				leaf hostname {
					type string;
				}

				leaf platform {
					type string;
				}

				leaf mac {
					type yang:mac-address;
				}

				leaf bgp_asn {
					type leafref {
						path "/sbg:sonic-bgp-global/sbg:BGP_GLOBALS/sbg:BGP_GLOBALS_LIST[sbg:vrf_name=current()/../vrf_name]/sbg:local_asn";
					}
				}

				leaf default_pfcwd_status {
					type enumeration {
						enum enable;
						enum disable;
					}
				}

				leaf default_bgp_status {
					type scommon:admin-status;
				}

				leaf docker_routing_config_mode {
					type enumeration {
						enum unified;
						enum separated;
					}
				}

				leaf deployment_id {
					type uint8 {
						range "0..255";
					}
				}

				leaf type {
					type enumeration {
						enum ToRRouter;
						enum LeafRouter;
					}
				}
			}
		}
	}
}
