module sonic-vlan-deviation {
	namespace "http://github.com/Azure/sonic-vlan-deviation";
	prefix svd;
	yang-version 1.1;

	/*
	import sonic-vlan {
		prefix svlan;
	}
	*/

	organization
		"SONiC";

	contact
		"SONiC";

	description
		"SONIC VLAN deviation file";

	revision 2019-05-15 {
		description
			"Initial revision.";
	}

	/*
	deviation /svlan:sonic-vlan/svlan:VLAN/svlan:name {
		deviate replace {
			type string {
				// Supports 3K VLANs 
				pattern "Vlan([1-3][0-9]{3}|[1-9][0-9]{2}|[1-9][0-9]|[1-9])";
			}
		}
	}
	*/
}
