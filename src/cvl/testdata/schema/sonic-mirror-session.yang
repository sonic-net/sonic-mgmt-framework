module sonic-mirror-session {
	namespace "http://github.com/Azure/sonic-mirror-session";
	prefix sms;

	import ietf-inet-types {
		prefix inet;
	}

	organization
		"SONiC";

	contact
		"SONiC";

	description
		"SONiC MIRROR SESSION";

	revision 2019-05-15 {
		description
			"Initial revision.";
	}

	container sonic-mirror-session {

		container MIRROR_SESSION {

			list MIRROR_SESSION_LIST {
				key "name";

				leaf name {
					type string;
				}

				leaf src_ip {
					type inet:ipv4-address;
				}

				leaf dst_ip {
					type inet:ipv4-address;
				}

				leaf gre_type {
					type string;
				}

				leaf dscp {
					type uint8;
				}

				leaf ttl {
					type uint8;
				}

				leaf queue {
					type uint8;
				}
			}
		}
	}
}
