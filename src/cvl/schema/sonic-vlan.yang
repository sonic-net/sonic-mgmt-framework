module sonic-vlan {
	namespace "http://github.com/Azure/sonic-vlan";
	prefix svlan;
	yang-version 1.1;

	import ietf-yang-types {
		prefix yang;
	}

	import sonic-common {
		prefix scommon;
	}

	import sonic-port {
		prefix prt;
	}

	import sonic-portchannel {
		prefix spc;
	}

	organization
		"BRCM";

	contact
		"BRCM";

	description
		"SONIC VLAN";

	revision 2019-05-15 {
		description
			"Initial revision.";
	}


	container sonic-vlan {

		list VLAN { 
			key "name";
			must "./name = concat('Vlan', string(./vlanid))"{
				error-app-tag vlan-invalid;
			}

			leaf name {
				type string {
					pattern "Vlan(409[0-5]|40[0-8][0-9]|[1-3][0-9]{3}|[1-9][0-9]{2}|[1-9][0-9]|[1-9])" {
						error-message "Invalid Vlan name pattern";
						error-app-tag vlan-name-invalid;
					}
				}
			}

			leaf vlanid {
				mandatory true;
				type uint16 {
					range "1..4095" {
						error-message "Vlan ID out of range";
						error-app-tag vlanid-invalid;
					}
				}
			}

			leaf-list members {
				 must "count(../members[text()=/spc:sonic-portchannel/" +
                                      "spc:PORTCHANNEL_MEMBER[spc:ifname=current()]/spc:name]) = 0 and " +
                                      "count(../members[text()=/spc:sonic-portchannel/" +
                                      "spc:PORTCHANNEL_MEMBER[spc:name=current()]/spc:ifname]) = 0 " {
                                       error-message "A vlan interface member cannot be part of portchannel which is already a vlan member";
                                }


				type union {
					type leafref {
						path "/prt:sonic-port/prt:PORT/prt:ifname";
					}
					type leafref {
						path "/spc:sonic-portchannel/spc:PORTCHANNEL/spc:name";
					}
				}
			}
		}

		list VLAN_MEMBER { 
			key "name ifname";

			leaf name {
				type leafref {
					path "../../VLAN/name";
				}
			}

			leaf ifname {
				type leafref {
					path "/prt:sonic-port/prt:PORT/prt:ifname";
				}
			}

			leaf tagging_mode {
				type scommon:tagging_mode;
				default tagged;
			}
		}

	}

}
