module sonic-bgp-neighbor {
	namespace "http://github.com/Azure/sonic-bgp-neighbor";
	prefix sbn;

	import ietf-yang-types {
		prefix yang;
	}

	import ietf-inet-types {
                prefix inet;
        }

	import sonic-common {
		prefix scommon;
	}

	import sonic-port {
		prefix prt;
	}

	organization
		"BRCM";

	contact
		"BRCM";

	description
		"SONIC BGP NEIGHBOR";

	revision 2019-07-02 {
		description
			"Initial revision.";
	}

	container sonic-bgp-neighbor {
		list BGP_NEIGHBOR {
			key "ipaddress";

			leaf ipaddress{
				type inet:ip-address;
			}

			leaf rrclient {
				type uint8 {
					range "0..255";
				}
			}

			leaf admin_status{
				type scommon:admin-status;
			}

			leaf peer_addr{
				type inet:ip-address;
			}

			leaf name {
				type string;
			}

			leaf local_addr {
				type inet:ipv4-address;
			}

			leaf nhopself {
				type uint8 {
					range "0..255";
				}
			}

			leaf holdtime {
				type uint8 {
					range "0..255";
				}
			}

			leaf asn {
				type uint64;
			}

			leaf keepalive {
				type uint8 {
					range "0..255";
				}
			}
		}
	}
}
