module sonic-ifa {
    namespace "http://github.com/Azure/sonic-ifa";
    prefix ifa;

    import ietf-inet-types {
        prefix inet;
    }

    import sonic-acl {
        prefix sacl;
    }

    organization
        "SONiC";

    contact
        "SONiC";

    description
        "SONIC TAM IFA";

    revision 2019-05-15 {
        description
            "Initial revision.";
    }

    container sonic-ifa {

        container TAM_INT_FEATURE_TABLE {

            list TAM_INT_FEATURE_TABLE_LIST {
                key "feature";
                max-elements "1";

                leaf feature {
                    type string;
                    default "feature";
                }

                leaf enable {
                    type boolean;
                }
            }
        }

        container TAM_DEVICE_TABLE {

            list TAM_DEVICE_TABLE_LIST {
                key "device";
                max-elements "1";

                leaf device {
                    type string;
                    default "device";
                }

                leaf deviceid {
                    type uint16;
                }
            }
        }

        container TAM_COLLECTOR_TABLE {

            list TAM_COLLECTOR_TABLE_LIST {
                key "name";

                leaf name {
                    type string;
                }

                leaf ipaddress-type {
                    type enumeration {
                        enum ipv4;
                        enum ipv6;
                    }
                }

                leaf ipaddress {
                    type inet:ipv4-address;
                }
                leaf port {
                    type uint16;
                }
            }
        }


        container TAM_INT_IFA_FLOW_TABLE {

            list TAM_INT_IFA_FLOW_TABLE_LIST {
                key "name";

                leaf name {
                    type string;
                }

                leaf acl-table-name {
                    type leafref {
                        path "/sacl:sonic-acl/sacl:ACL_TABLE/sacl:ACL_TABLE_LIST/sacl:aclname";
                    }
                }

                leaf acl-rule-name {
                    type leafref {
                        path "/sacl:sonic-acl/sacl:ACL_RULE/sacl:ACL_RULE_LIST/sacl:rulename";
                    }
                }

                leaf sampling-rate {
                    type uint16 {
                        range "1..10000"{
                            error-message "Invalid IFA flow sampling rate.";
                        }
                    }
                }

                leaf collector {
                    type leafref {
                        path "../../../TAM_COLLECTOR_TABLE/TAM_COLLECTOR_TABLE_LIST/name";
                    }
                }
            }
        }
    }
}
