module sonic-dscp-tc-map {
	namespace "http://github.com/Azure/sonic-dscp-tc-map";
	prefix dtm;

	import ietf-yang-types {
		prefix yang;
	}

	import sonic-common {
		prefix scommon;
	}

	import sonic-port {
		prefix sif;
	}

	organization
		"BRCM";

	contact
		"BRCM";

	description
		"SONIC DSCP_TO_TC_MAP";

	revision 2019-05-15 {
		description
			"Initial revision.";
	}

	container sonic-dscp-tc-map {	
		list DSCP_TO_TC_MAP {
			key "name";
			scommon:map-list true; //special conversion for map tables
			scommon:map-leaf "dscp tc_num"; //every key:value pair is mapped to list keys, e.g. "1":"7" ==> tc_num=1, dscp=7

			leaf name {
				type string;
			}

			list DSCP_TO_TC_MAP { //this is list inside list for storing mapping between two fields
				key "dscp tc_num";

				leaf tc_num {
					type string {
						pattern "[0-9]?"{
							error-message "Invalid Traffic Class number";
							error-app-tag tc-num-invalid;
						}
					}
				}

				leaf dscp {
					type string {
						pattern "[1-9][0-9]?|[0-9]?";
					}
				}
			}

		}
	}
}
