module sonic-mgmt-port {
    namespace "http://github.com/Azure/sonic-mgmt-port";
    prefix prt;

    import ietf-yang-types {
        prefix yang;
    }

    import sonic-common {
        prefix scommon;
    }

    organization
        "DELL";

    contact
        "DELL";

    description
        "SONIC Management Interface";

    revision 2019-09-17 {
        description
            "Initial revision.";
    }


    container sonic-mgmt-port {
        list MGMT_PORT {
            key "ifname";

            leaf ifname {
                type string {
                    pattern "eth([1-3][0-9]{3}|[1-9][0-9]{2}|[1-9][0-9]|[0-9])"{
                        error-message "Invalid interface name";
                    error-app-tag interface-name-invalid;
                }
                }
            }

            leaf speed {
                type uint64;
            }

            leaf autoneg {
                type boolean;
            }

            leaf alias {
                type string;
            }

            leaf description {
                type string;
            }

            leaf mtu{
                type uint32;
            }

            leaf admin_status {
                type scommon:admin-status;
            }
        }
    }
}
