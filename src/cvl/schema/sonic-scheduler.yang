module sonic-scheduler {
	namespace "http://github.com/Azure/sonic-scheduler";
	prefix sch;

	import ietf-yang-types {
		prefix yang;
	}

	import sonic-common {
		prefix scommon;
	}

	organization
		"BRCM";

	contact
		"BRCM";

	description
		"SONIC SCHEDULER";

	revision 2019-05-15 {
		description
			"Initial revision.";
	}

	container sonic-scheduler {
		list SCHEDULER {
			key "name";

			leaf name{
				type string;
			}

			leaf type {
				type enumeration {
					enum DWRR;
					enum WRR;
					enum PRIORITY;
				}
			}

			leaf weight {
				type uint8 {
					range "0..255";
				}
			}

			leaf priority {
				type uint8 {
					range "0..9";
				}
			}
		}
	}
}
