module sonic-spanning-tree {
    namespace "http://github.com/Azure/sonic-spanning-tree";
    prefix sstp;
    yang-version 1.1;

    import sonic-common {
        prefix scommon;
    }

    import sonic-port {
        prefix prt;
    }

    import sonic-portchannel {
        prefix spc;
    }

    import sonic-pf-limits {
        prefix spf;
    }

    organization
        "BRCM";

    contact
        "BRCM";

    description
        "SONIC Spanning-tree";

    revision 2019-09-21 {
        description
            "Initial revision.";
    }

    typedef interface-type {
        type union { 
            type leafref {
                path "/prt:sonic-port/prt:PORT/prt:ifname";
            }
            type leafref {
                path "/spc:sonic-portchannel/spc:PORTCHANNEL/spc:name";
            }
        }
    }

    grouping vlanModeAttr {
        leaf forward_delay {
            type uint8 {
                range "4..30" {
                    error-message "Invalid Forwarding Delay value.";
                }
            }
            units seconds;
            default 15;
        }

        leaf hello_time {
            type uint8 {
                range "1..10" {
                    error-message "Invalid Hello Time value.";
                }
            }
            units seconds;
            default 2;
        }

        leaf max_age {
            type uint8 {
                range "6..40" {
                    error-message "Invalid Maximum Age Time value.";
                }
            }
            units seconds;
            default 20;
        }

        leaf priority {
            type uint16 {
                range "0..61440" {
                    error-message "Invalid Bridge Priority value.";
                }
            }
            units seconds;
            default 20;
        }
    }

    grouping interfaceAttr {
        leaf path_cost {
            type uint64 {
                range "1..200000000" {
                    error-message "Invalid Port Path Cost value.";
                }
            }
            default 200;
        }

        leaf priority {
            type uint8 {
                range "0..240" {
                    error-message "Invalid Port Priority value.";
                }
            }
            default 128;
        }
    }

    container sonic-spanning-tree {

        /*
        container STP {
            list STP_LIST {
                key "keyleaf";

                leaf keyleaf {
                    type enumeration {
                        enum GLOBAL;
                    }
                }

                leaf mode {
                    type enumeration {
                        enum pvst;
                        enum rpvst;
                        enum mstp;
                        enum rstp;
                    }
                }

                leaf rootguard_timeout {
                    type uint16 {
                        range "5..600" {
                            error-message "Invalid Root-guard Timeout value.";
                        }
                    }
                    units seconds;
                    default 30;
                }

                uses vlanModeAttr;
            }
        }

        container STP_VLAN {
            list STP_VLAN_LIST {
                key "name";
                must "./name = concat('Vlan', string(./vlanid))" {
                    error-app-tag vlan-invalid;
                }

                leaf name {
                    type string {
                        pattern "Vlan(409[0-5]|40[0-8][0-9]|[1-3][0-9]{3}|[1-9][0-9]{2}|[1-9][0-9]|[1-9])" {
                            error-message "Invalid Vlan name pattern";
                            error-app-tag vlan-name-invalid;
                        }
                    }
                }

                leaf vlanid {
                    mandatory true;
                    type uint16 {
                        range "1..4095" {
                            error-message "Vlan ID out of range";
                            error-app-tag vlanid-invalid;
                        }
                    }
                }

                leaf enabled {
                    type boolean;
                }

                uses vlanModeAttr;
            }
        }

        container STP_VLAN_INTF {
            list STP_VLAN_INTF_LIST {
                key "vlan-name ifname";

                leaf vlan-name {
                    type leafref {
                        path "../../../STP_VLAN/STP_VLAN_LIST/name";
                    }
                }

                leaf ifname {
                    type interface-type;
                }

                uses interfaceAttr;
            }
        }

        container STP_INTF {
            list STP_INTF_LIST {
                key "ifname";

                leaf ifname {
                    type interface-type;
                }

                leaf enabled {
                    type boolean;
                }

                leaf root_guard {
                    type boolean;
                }

                leaf bpdu_guard {
                    type boolean;
                }

                leaf bpdu_guard_do_disable {
                    type boolean;
                }

                leaf uplink_fast {
                    type boolean;
                }

                leaf portfast {
                    type boolean;
                }

                uses interfaceAttr;

                // For RPVST+
                leaf edge_port {
                    //when ("../../../STP/STP_LIST/mode='rpvst'");
                    type boolean;
                }

                leaf pt2pt_mac {
                    //when ("../../../STP/STP_LIST/mode='rpvst'");
                    type boolean;
                }
            }
        }
        */

        list STP {
            key "keyleaf";

            leaf keyleaf {
                type enumeration {
                    enum GLOBAL;
                }
            }

            leaf mode {
                type enumeration {
                    enum pvst;
                    enum rpvst;
                    enum mstp;
                    enum rstp;
                }
            }

            leaf rootguard_timeout {
                type uint16 {
                    range "5..600" {
                        error-message "Invalid Root-guard Timeout value.";
                    }
                }
                units seconds;
                default 30;
            }

            uses vlanModeAttr;
        }

        list STP_VLAN {
            key "name";
            /*must "./name = concat('Vlan', string(./vlanid))" {
                error-app-tag vlan-invalid;
            }*/

            leaf name {
                type string {
                    pattern "Vlan(409[0-5]|40[0-8][0-9]|[1-3][0-9]{3}|[1-9][0-9]{2}|[1-9][0-9]|[1-9])" {
                        error-message "Invalid Vlan name pattern";
                        error-app-tag vlan-name-invalid;
                    }
                }
            }

            leaf vlanid {
                mandatory true;
                type uint16 {
                    range "1..4095" {
                        error-message "Vlan ID out of range";
                        error-app-tag vlanid-invalid;
                    }
                }
            }

            leaf enabled {
                type boolean;
            }

            uses vlanModeAttr;
        }

        list STP_INTF {
            key "ifname";

            leaf ifname {
                type string;
                //type interface-type;
            }

            leaf enabled {
                type boolean;
            }

            leaf root_guard {
                type boolean;
            }

            leaf bpdu_guard {
                type boolean;
            }

            leaf bpdu_filter {
                type boolean;
            }

            leaf bpdu_guard_do_disable {
                type boolean;
            }

            leaf uplink_fast {
                type boolean;
            }

            leaf portfast {
                type boolean;
            }

            uses interfaceAttr;

            // For RPVST+
            leaf edge_port {
                //when ("../../STP/mode='rpvst'");
                type boolean;
            }

            leaf pt2pt_mac {
                //when ("../../STP/mode='rpvst'");
                type boolean;
            }
        }

        list STP_VLAN_INTF {
            key "vlan-name ifname";

            leaf vlan-name {
                /*type leafref {
                    path "../../STP_VLAN/name";
                }*/
                type string {
                    pattern "Vlan(409[0-5]|40[0-8][0-9]|[1-3][0-9]{3}|[1-9][0-9]{2}|[1-9][0-9]|[1-9])" {
                        error-message "Invalid Vlan name pattern";
                        error-app-tag vlan-name-invalid;
                    }
                }
            }

            leaf ifname {
                type string;
                //type interface-type;
            }

            uses interfaceAttr;
        }
    }
}
