module sonic-portchannel-interface {
	namespace "http://github.com/Azure/sonic-portchannel-interface";
	prefix spchint;

	import ietf-yang-types {
		prefix yang;
	}

	import ietf-inet-types {
                prefix inet;
        }

	import sonic-common {
		prefix scommon;
	}

	import sonic-portchannel {
		prefix spc;
	}

	organization
		"BRCM";

	contact
		"BRCM";

	description
		"SONIC PORTCHANNEL INTERFACE";

	revision 2019-07-02 {
		description
			"Initial revision.";
	}

	container sonic-portchannel-interface {
		list PORTCHANNEL_INTERFACE {
			key "pch_name ip_prefix";

			leaf pch_name{
				type leafref {
					path "/spc:sonic-portchannel/spc:PORTCHANNEL/spc:name";
                                }
			}

			leaf ip_prefix {
				 mandatory true;
                                 type inet:ip-prefix;

			}
		}
	}
}
