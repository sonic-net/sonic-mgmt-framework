module sonic-mgmt-interface {
    namespace "http://github.com/Azure/sonic-mgmt-interface";
    prefix sint;

    import ietf-yang-types {
        prefix yang;
    }

    import ietf-inet-types {
        prefix inet;
    }

    import sonic-common {
        prefix scommon;
    }

    import sonic-mgmt-port {
        prefix mgmtprt;
    }

    organization
        "DELL";

    contact
        "DELL";

    description
        "SONIC MANAGEMENT INTERFACE";

    revision 2019-07-02 {
        description
            "Initial revision.";
    }

    container sonic-mgmt-interface {
        list MGMT_INTERFACE {
            key "portname ip_prefix";

            leaf portname{
                type leafref {
                    path "/mgmtprt:sonic-mgmt-port/mgmtprt:MGMT_PORT/mgmtprt:ifname";
                }
            }

            leaf ip_prefix {
                mandatory true;
                type inet:ip-prefix;

            }
            leaf gwaddr {
                type inet:ip-prefix;
            }
        }
    }
}
