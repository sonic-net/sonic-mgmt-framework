module sonic-device-neighbor {
	namespace "http://github.com/Azure/sonic-device-neighbor";
	prefix sdn;

	import ietf-yang-types {
		prefix yang;
	}

	import ietf-inet-types {
                prefix inet;
        }

	import sonic-common {
		prefix scommon;
	}

	import sonic-port {
		prefix prt;
	}


	organization
		"BRCM";

	contact
		"BRCM";

	description
		"SONIC DEVICE NEIGHBOR";

	revision 2019-07-02 {
		description
			"Initial revision.";
	}

	container sonic-device-neighbor {
		list DEVICE_NEIGHBOR {
			key "name";

			leaf name{
				type string;
			}

			leaf mgmt_addr{
				type inet:ip-address;
			}

			leaf hwsku {
				type string;
			}

			leaf lo_addr {
				type inet:ip-address;
			}

			leaf local_port {
				type leafref {
                                        path "/prt:sonic-port/prt:PORT/prt:ifname";
                                }
			}

			leaf type {
				type enumeration {
                                        enum ToRRouter;
                                        enum LeafRouter;
                                }
			}

			leaf port {
				type leafref {
                                        path "/prt:sonic-port/prt:PORT/prt:ifname";
                                }
			}
		}
	}
}
