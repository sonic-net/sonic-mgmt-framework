module sonic-queue {
	namespace "http://github.com/Azure/sonic-queue";
	prefix squeue;

	import ietf-yang-types {
		prefix yang;
	}

	import sonic-common {
		prefix scommon;
	}

	import sonic-port {
		prefix prt;
	}

	import sonic-scheduler {
		prefix sch;
	}

	import sonic-wred-profile {
		prefix wrd;
	}

	organization
		"BRCM";

	contact
		"BRCM";

	description
		"SONIC QUEUE";

	revision 2019-05-15 {
		description
			"Initial revision.";
	}


	container sonic-queue {
		list QUEUE {
			key "ifname qindex";
			scommon:key-pattern "QUEUE|({ifname},)*|{qindex}"; //special pattern used for extracting keys from redis-key and populate the yang instance
									   // Total list instances = number(key1) * number(key2) * number(key3)

			leaf ifname {
				type leafref {
					path "/prt:sonic-port/prt:PORT/prt:ifname";
				}
			}

			leaf qindex {
				type string {
					pattern "[0-8]((-)[0-8])?"{
						error-message "Invalid Q-index";
						error-app-tag qindex-invalid;
					}
				}
			}

			leaf scheduler {
				type leafref {
					path "/sch:sonic-scheduler/sch:SCHEDULER/sch:name";
				}
			}

			leaf wred_profile {
				type leafref {
					path "/wrd:sonic-wred-profile/wrd:WRED_PROFILE/wrd:name";
				}
			}
		}
	}
}
